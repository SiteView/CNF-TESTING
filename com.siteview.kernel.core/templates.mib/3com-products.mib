-- **********************************************************************
-- This is the 3Com Enterprise MIB.
--
-- This MIB is specifically for the Transcend products.
-- 
-- MIB Version:         
--
-- Comments:            This defines the structure of the 3Com branch.
--
-- History:
-- Date         Author          Reason for Change
-- 1 Sep 94     Paul J Moran        Created
-- 28 Nov 94    Paul J Moran        Added LinkSwitch100 OIDs
-- 10 Jan 95    Ed Heiner           Added LANplex Systems MIB,
--                                  LANplex Optional FDDI MIB,
--                                  LANplex 2500/2016 sysOids, and
--                                  new LANplex 6000 sysOids.
-- 31 Jan 95    Paul J Moran        Added more LinkSwitch100 OIDs
-- 21 Feb 95    Danny Propp         Added NCD products - 
--                                    New atm product group including
--                                    CELLplex 7000,7200 OIDs.
--                                    New linkSwitch500 and
--                                    linkSwitch2700Atm OIDs.
-- 27 Feb 95    David Chuang,Srinath Candadai   
--        Added FMS100(Fast Ethernet Hub) OIDs
--
-- 15 Mar 95    Kiho Yum            Added NSD products -
--                                    NbroTrLarge, NbroTrHuge, mp6EthFl,
--                                    ethV3, mp6EthFl, and ethV3Fl
--
--  8 May 95    Danny Propp         Added NCD product - LinkSwitch2700Tli.
--                                  Updated LinkSwitch2700Atm's name.
--                                  Added ncdMibs OID.
--
-- 15 May 95    Kiho Yum            Added NSD products - 
--                                    cs2x00to, cs2x00tlo, cs3x00to, cs3x00tlo
--                                    series2500, series3000, nbroFw,
--                                    added AA sw pkg to all brouter products
--                                    added AB sw pkg to all brouter products
--                                    added BF sw pkg to all brouter products
--
-- 16 May 95    Ed Heiner           Added SD products -
--                                    lss2000, linkSwitch-2200-2,
--                                    lanplex-60xx-System-2,
--                                    lanplex-60xx-Chassis-2,
--                                    lanplex-60xx-ESM-2,
--                                    lanplex-60xx-EFSM-2
--                                    Revised new switching module names
--                                    (lps60xxFESM -> lps60xxEFSM).
--
-- 19 Jun 95    Ed Heiner           Added SD products -
--                                    lanplex-2500-3, lanplex-2016-3, and
--                                    linkSwitch-2200-3.
--
-- 22 Jun 95 David Chuang & Srinath Candadai, Added NAD products -
--          FMS100 management only system
--
-- 26 Jun 95 Paul J Moran Added linkBuilderPresley
--                              rename linkSwitch100 to linkSwitch1000
--                              Added linkSwitch3000
--
--  3 Jul 95    Ed Heiner           Added SD products -
--                                    lanplex-60xx-System-3,
--                                    lanplex-60xx-Chassis-3,
--                                    lanplex-60xx-ESM-3, and
--                                    lanplex-60xx-EFSM-3.
-- 8 Aug 95 Paul J Moran 
-- rename linkBuilderPresley to officeStack-Hub8M
--
-- 28 Nov 95    Danny Propp           CELLplex7200 replaced by
--                                      CELLplex7000-modules;
--                                    New NCD CELLplex7000 modules added -
--                                      - CELLplex7x00-moduleBridge
--                                      - CELLplex7200-module
--                                      - CELLplex7200F-module
--                                      - CELLplex7400-module
--
-- 06 Dec 95    Kiho Yum              Added OIDs for NETBuilder
--                                    Remote Office Token Ring Isdn
--                                    products.  Added nbro numbers to
--                                    OID descriptors.
--
-- 06 Dec 95    Kiho Yum              Swapped OIDs for nbroTrHuge and 
--                                    nbroTrIsdn
-- 
-- 30 Jan 96 Paul J Moran 
-- rename officeStack to officeConnect
-- add extra linkSwitch3000 module
--
-- 6 Feb 96 Paul J Moran 
-- add linkSwitch1000MSH sysObjID
--
-- 08 Feb 96    Danny Propp           Changed all CELLplex names to cELLplex.
--                                    Changed cELLplex7000 modules/cards
--                                    names.
--                                    Added cELLplex-7600card.
--
-- 13 Feb 96 Paul J Moran 
-- add superStack card ids
--
--
-- 29 Feb 96  David Chuang & Srinath Candadai     Added rptrGroupObjectID for FMS 100
--        (100BaseT4) repeater. 
--
-- 06 Mar 96    Kiho Yum              Added OIDs for new NETBuilder
--                                    ATM board, nbro2Eth, and nbro2EthIsdn.
--
-- 07 Mar 96 John Scano Added OIDs for
--     TRSM Module
--     TMM Module
--     FSM Module
--     SS-2
--    For agent revisions 4,5,6,7
--
-- 15 March 96 Paul J Moran
-- Added linkswitch cards for the OnCore
--
-- 20 March 96 Paul J Moran
-- ATMO module for superStack Switch1000/3000
--
-- 20 March 96 Kiho Yum               Added OIDs for new NETBuilder
--                                    flat FDDI boards
-- 
-- 15 April 96 Paul J Moran
-- Add oids for the LinkSwitch2000/Token Ring
--
-- 25 April 96 Paul J Moran
-- Changed linkSwitch1000MSH to mshSwitch1005
--
-- 29 April 96 Paul J Moran
-- Added main branch for the VLAN Server
--
-- 23 May 96 Kiho Yum
-- Added main branch for terminal servers
--
-- 29 May 96 Kiho Yum
-- Added product oids for Office Connect Routers
--
-- 3 June 96 Paul J Moran
-- Added more linkswitch cards for the OnCore
--
-- 21June 96 Paul J Moran
-- Added yet more linkswitch card ids for the OnCore
-- Added sysObjectId for new SuperStack Desktop Switch
--
-- 8 July 1996 Paul J Moran
-- Added card id for new SuperStack Desktop Switch
--
-- **********************************************************************
--      Copyright 3Com Technologies Limited. (1991-1996)
-- **********************************************************************

A3Com-products-MIB DEFINITIONS ::= BEGIN
    IMPORTS
        enterprises FROM RFC1155-SMI;

--
-- This MIB contains 3com product OIDs (used in sysObjectID)
--

a3Com                   OBJECT IDENTIFIER ::= { enterprises 43 }
products                OBJECT IDENTIFIER ::= { a3Com 1 }
brouterMIB              OBJECT IDENTIFIER ::= { a3Com 2 }
amp-mib                 OBJECT IDENTIFIER ::= { a3Com 3 }
genericTrap             OBJECT IDENTIFIER ::= { a3Com 4 }
viewBuilderApps         OBJECT IDENTIFIER ::= { a3Com 5 }
specificTrap            OBJECT IDENTIFIER ::= { a3Com 6 }
linkBuilder3GH-mib      OBJECT IDENTIFIER ::= { a3Com 7 }
linkBuilder10BTi-mib    OBJECT IDENTIFIER ::= { a3Com 8 }
linkBuilderECS-mib      OBJECT IDENTIFIER ::= { a3Com 9 }
generic                 OBJECT IDENTIFIER ::= { a3Com 10 }
netBuilder-mib          OBJECT IDENTIFIER ::= { a3Com 11 }
lBridgeECS-mib          OBJECT IDENTIFIER ::= { a3Com 12 }
deskMan                 OBJECT IDENTIFIER ::= { a3Com 13 }
linkBuilderMSH-mib      OBJECT IDENTIFIER ::= { a3Com 14 }
a3ComUnused15           OBJECT IDENTIFIER ::= { a3Com 15 }
a3comFddiWGHubMib       OBJECT IDENTIFIER ::= { a3Com 16 }
linkSwitch              OBJECT IDENTIFIER ::= { a3Com 17 }
linkSwitch1000-mib      OBJECT IDENTIFIER ::= { a3Com 18 }
linkBuilderFMS100-mib   OBJECT IDENTIFIER ::= { a3Com 19 }
ncdMibs                 OBJECT IDENTIFIER ::= { a3Com 20 }
officeConnect-Hub8M-mib OBJECT IDENTIFIER ::= { a3Com 21 }
linkSwitch2000TR-mib    OBJECT IDENTIFIER ::= { a3Com 22 }
vlanServer-mib          OBJECT IDENTIFIER ::= { a3Com 23 }
terminalServerMib       OBJECT IDENTIFIER ::= { a3Com 24 }

terminalServer          OBJECT IDENTIFIER ::= { products 1 }          
dedicatedBridgeServer   OBJECT IDENTIFIER ::= { products 2 }          
dedicatedRouteServer    OBJECT IDENTIFIER ::= { products 3 }          
brouter                 OBJECT IDENTIFIER ::= { products 4 }          
genericMSWorkstation    OBJECT IDENTIFIER ::= { products 5 }          
genericMSServer         OBJECT IDENTIFIER ::= { products 6 }          
genericUnixServer       OBJECT IDENTIFIER ::= { products 7 }          
hub                     OBJECT IDENTIFIER ::= { products 8 }  
cards                   OBJECT IDENTIFIER ::= { products 9 }       
chipSets                OBJECT IDENTIFIER ::= { products 10 }
oem                     OBJECT IDENTIFIER ::= { products 11 }
atm                     OBJECT IDENTIFIER ::= { products 12 }

--
-- the following identifiers are assigned to 3com terminal servers
--        

cs2500                  OBJECT IDENTIFIER ::= { terminalServer 1 }
cs2600                  OBJECT IDENTIFIER ::= { terminalServer 2 } 
cs2000                  OBJECT IDENTIFIER ::= { terminalServer 3 }
cs1                     OBJECT IDENTIFIER ::= { terminalServer 4 }
cs210                   OBJECT IDENTIFIER ::= { terminalServer 5 }
cs2100                  OBJECT IDENTIFIER ::= { terminalServer 6 }
cs3000                  OBJECT IDENTIFIER ::= { terminalServer 7 }  
cs3100                  OBJECT IDENTIFIER ::= { terminalServer 8 }          
callisto                OBJECT IDENTIFIER ::= { terminalServer 9 } 
termServerPlatform      OBJECT IDENTIFIER ::= { terminalServer 10 }

--
-- the following ids are assigned under a3Com.products.terminalServer.cs2500
--

cs2500to                OBJECT IDENTIFIER ::= { cs2500 1 }
cs2500tlo               OBJECT IDENTIFIER ::= { cs2500 2 }

--
-- the following ids are assigned under a3Com.products.terminalServer.cs2600
--

cs2600to                OBJECT IDENTIFIER ::= { cs2600 1 }
cs2600tlo               OBJECT IDENTIFIER ::= { cs2600 2 }

--
-- the following ids are assigned under a3Com.products.terminalServer.cs2000
--

cs2000to                OBJECT IDENTIFIER ::= { cs2000 1 }
cs2000tlo               OBJECT IDENTIFIER ::= { cs2000 2 }

--
-- the following ids are assigned under a3Com.products.terminalServer.cs2100
--

cs2100to                OBJECT IDENTIFIER ::= { cs2100 1 }
cs2100tlo               OBJECT IDENTIFIER ::= { cs2100 2 }

--
-- the following ids are assigned under a3Com.products.terminalServer.cs3000
--

cs3000to                OBJECT IDENTIFIER ::= { cs3000 1 }
cs3000tlo               OBJECT IDENTIFIER ::= { cs3000 2 }

--
-- the following ids are assigned under a3Com.products.terminalServer.cs3100
--

cs3100to                OBJECT IDENTIFIER ::= { cs3100 1 }
cs3100tlo               OBJECT IDENTIFIER ::= { cs3100 2 }

--
-- the following identifiers are assigned to 3com terminal server platforms
--

series1                 OBJECT IDENTIFIER ::= { termServerPlatform 1 }
series200               OBJECT IDENTIFIER ::= { termServerPlatform 2 }
callistoPlatfor         OBJECT IDENTIFIER ::= { termServerPlatform 3 }
series2500              OBJECT IDENTIFIER ::= { termServerPlatform 4 }
series3000              OBJECT IDENTIFIER ::= { termServerPlatform 5 }


--
-- the following identifiers are assigned to 3com brouters
--

netbuilder1        OBJECT IDENTIFIER ::= { brouter 1 }  -- not used
netbuilder2        OBJECT IDENTIFIER ::= { brouter 2 }  -- >= 6.2
lBridgeECS         OBJECT IDENTIFIER ::= { brouter 3 }
netbuilderTrRA     OBJECT IDENTIFIER ::= { brouter 4 }  -- 2 port nbtr NBTR Remote Access
brouterPlatform    OBJECT IDENTIFIER ::= { brouter 5 }
netbuilderRem      OBJECT IDENTIFIER ::= { brouter 6 }  -- 4 port nb1 NB Remote
netbuilderRA       OBJECT IDENTIFIER ::= { brouter 7 }  -- 2 port nb1 NB Remote Access
netbuilderRC       OBJECT IDENTIFIER ::= { brouter 8 }  -- 2 port boundary rtr NB Remote Control
netbuilderTrRem    OBJECT IDENTIFIER ::= { brouter 9 }  -- 4 port tok.ring nb1 NBTR Remote
netbuilderTrRC     OBJECT IDENTIFIER ::= { brouter 10 } -- tok.ring boundary rtr NBTR Remote Control
nb2_4              OBJECT IDENTIFIER ::= { brouter 11 } -- 4 port nb2
nb2_8              OBJECT IDENTIFIER ::= { brouter 12 } -- 8 port nb2
nbro               OBJECT IDENTIFIER ::= { brouter 13 } -- netbuilder Rem. Office (spectre)
brouterBoards      OBJECT IDENTIFIER ::= { brouter 14 }
netbuilderLocal    OBJECT IDENTIFIER ::= { brouter 15 } -- 2 Lan nb1 NB Local
netbuilderTrLocal  OBJECT IDENTIFIER ::= { brouter 16 } -- 2 Lan nbtr NBTR Local
netbuilderRC1x2    OBJECT IDENTIFIER ::= { brouter 17 } -- NB Rem Ctl w/2 wan ports
netbuilderTrRC1x2  OBJECT IDENTIFIER ::= { brouter 18 } -- NBTR Rem Ctl w/2 wan ports
casper             OBJECT IDENTIFIER ::= { brouter 19 } -- Spectre Large
spectreHuge        OBJECT IDENTIFIER ::= { brouter 20 } -- Spectre Huge
spectreIsdn        OBJECT IDENTIFIER ::= { brouter 21 } -- Spectre ISDN
nb2_8_4fddi        OBJECT IDENTIFIER ::= { brouter 22 } -- 8 port nb2 capable of 4 fddi sets
nb2_8_dualwide     OBJECT IDENTIFIER ::= { brouter 23 } -- 8 port nb2 w/dual wide slots 4 crew
brouterBrdFwVers   OBJECT IDENTIFIER ::= { brouter 24 } -- fw versions
brouterBrdSwVers   OBJECT IDENTIFIER ::= { brouter 25 } -- sw versions
spectreIsdnHuge    OBJECT IDENTIFIER ::= { brouter 26 } -- Spectre ISDN
nbroTrLarge       OBJECT IDENTIFIER ::= { brouter 27 }--SpectreTR4x8
nbroTrIsdn         OBJECT IDENTIFIER ::= { brouter 28 } -- SpectreTrIsdn4x8
nbroTrHuge        OBJECT IDENTIFIER ::= { brouter 29 }--SpectreTrxxx
nbro2Eth          OBJECT IDENTIFIER ::= { brouter 30 } -- Spectre2Eth
nbro2EthIsdn      OBJECT IDENTIFIER ::= { brouter 31 } -- Spectre2EthIsdn
officeConnRtr     OBJECT IDENTIFIER ::= { brouter 32 } -- officeConnect


--
-- the following ids are assigned under a3Com.products.brouter.netbuilderTrRA
--
netbuilderTrRAbp   OBJECT IDENTIFIER ::= { netbuilderTrRA 1 }  -- NBTR Rem. Acc. w/Basic Prot. SW
netbuilderTrRAcp   OBJECT IDENTIFIER ::= { netbuilderTrRA 2 }  -- NBTR Rem. Acc. w/Compl. Prot. SW
netbuilderTrRAxw   OBJECT IDENTIFIER ::= { netbuilderTrRA 3 }  -- NBTR Rem. Acc w/Ext. WAN SW
netbuilderTrRAcx   OBJECT IDENTIFIER ::= { netbuilderTrRA 4 }  -- NBTR Rem. Acc. w/Con Svc SW
netbuilderTrRAba   OBJECT IDENTIFIER ::= { netbuilderTrRA 5 }  -- NBTR Rem. Acc. w/Bndry Rtg Clnt
netbuilderTrRAar   OBJECT IDENTIFIER ::= { netbuilderTrRA 6 }  -- NBTR Rem. Acc. w/Acc. Rtr SW
netbuilderTrRAsn   OBJECT IDENTIFIER ::= { netbuilderTrRA 7 }  -- NBTR Rem. Acc. w/SNA SW
netbuilderTrRArb   OBJECT IDENTIFIER ::= { netbuilderTrRA 8 }  -- NBTR RA w/RB SW
netbuilderTrRAff   OBJECT IDENTIFIER ::= { netbuilderTrRA 9 }  -- NBTR RA w/Full Feature SW
netbuidlerTrRAcf   OBJECT IDENTIFIER ::= { netbuilderTrRA 10 } -- NBTR RA w/CF SW
netbuilderTrRAbx   OBJECT IDENTIFIER ::= { netbuilderTrRA 11 } -- NBTR Rem Acc w/BX SW
netbuilderTrRAappn OBJECT IDENTIFIER ::= { netbuilderTrRA 12 } -- NBTR RAAcc w/Appn SW
netbuilderTrRAlm   OBJECT IDENTIFIER ::= { netbuilderTrRA 13 } -- NBTR RA w/L Sw
netbuilderTrRAlt   OBJECT IDENTIFIER ::= { netbuilderTrRA 14 } -- NBTR RA w/Lt Sw
netbuilderTrRAwm   OBJECT IDENTIFIER ::= { netbuilderTrRA 15 } -- NBTR RA w/Wm Sw
netbuilderTrRAwt   OBJECT IDENTIFIER ::= { netbuilderTrRA 16 } -- NBTR RA w/Wt Sw
netbuilderTrRAae   OBJECT IDENTIFIER ::= { netbuilderTrRA 17 } -- NBTR RA w/Ae Sw
netbuilderTrRAap   OBJECT IDENTIFIER ::= { netbuilderTrRA 18 } -- NBTR RA w/Ap Sw
netbuilderTrRAan   OBJECT IDENTIFIER ::= { netbuilderTrRA 19 } -- NBTR RA w/An Sw
netbuilderTrRAla   OBJECT IDENTIFIER ::= { netbuilderTrRA 20 } -- NBTR RA w/La Sw
netbuilderTrRAwa   OBJECT IDENTIFIER ::= { netbuilderTrRA 21 } -- NBTR RA w/Wa Sw
netbuilderTrRAaa   OBJECT IDENTIFIER ::= { netbuilderTrRA 22 } -- NBTR RA w/Aa Sw
netbuilderTrRAab   OBJECT IDENTIFIER ::= { netbuilderTrRA 23 } -- NBTR RA w/Ab Sw
netbuilderTrRAbf   OBJECT IDENTIFIER ::= { netbuilderTrRA 24 } -- NBTR RA w/Bf Sw


--
-- the following identifiers are assigned to brouterPlatform
--

nb1                OBJECT IDENTIFIER ::= { brouterPlatform 1 } -- nb1 platform
nb2                OBJECT IDENTIFIER ::= { brouterPlatform 2 } -- nb2 platform
nbroPlatform       OBJECT IDENTIFIER ::= { brouterPlatform 3 } -- netbuilder remote office platform
casperPlatform     OBJECT IDENTIFIER ::= { brouterPlatform 4 } -- Casper platform
spectreIsdnPform   OBJECT IDENTIFIER ::= { brouterPlatform 5 } -- spec.isdn pf
spectreIITr        OBJECT IDENTIFIER ::= { brouterPlatform 6 }--spec.IITr pf


--
-- the following id are assigned under a3Com.products.brouter.netbuilderRem
--

netbuilderRemBp   OBJECT IDENTIFIER ::= { netbuilderRem 1 }  -- nb Rem. w/Basic Prot
netbuilderRemCp   OBJECT IDENTIFIER ::= { netbuilderRem 2 }  -- nb Rem w/Compl Prot
netbuilderRemXw   OBJECT IDENTIFIER ::= { netbuilderRem 3 }  -- nb Rem w/Ext WAN
netbuilderRemCx   OBJECT IDENTIFIER ::= { netbuilderRem 4 }  -- nb Rem w/X25 Con Svc
netbuilderRemBa   OBJECT IDENTIFIER ::= { netbuilderRem 5 }  -- nb Rem w/Bndry Rtg
netbuilderRemAr   OBJECT IDENTIFIER ::= { netbuilderRem 6 }  -- nb Rem w/Acc Rtr SW
netbuilderRemSn   OBJECT IDENTIFIER ::= { netbuilderRem 7 }  -- nb Rem w/SNA SW
netbuilderRemRb   OBJECT IDENTIFIER ::= { netbuilderRem 8 }  -- nb Rem w/RB SW
netbuilderRemFf   OBJECT IDENTIFIER ::= { netbuilderRem 9 }  -- nb Remw/FF SW
netbuilderRemCf   OBJECT IDENTIFIER ::= { netbuilderRem 10 } -- nb Rem w/CF SW
netbuilderRemBx   OBJECT IDENTIFIER ::= { netbuilderRem 11 } -- nb Rem w/BX SW
netbuilderRemAppn OBJECT IDENTIFIER ::= { netbuilderRem 12 } -- nb Rem w/Appn SW
netbuilderRemLm   OBJECT IDENTIFIER ::= { netbuilderRem 13 } -- nb Rem w/Lm Sw
netbuilderRemLt   OBJECT IDENTIFIER ::= { netbuilderRem 14 } -- nb Rem w/Lt Sw
netbuilderRemWm   OBJECT IDENTIFIER ::= { netbuilderRem 15 } -- nb Rem w/Wm Sw
netbuilderRemWt   OBJECT IDENTIFIER ::= { netbuilderRem 16 } -- nb Rem w/Wt Sw
netbuilderRemAe   OBJECT IDENTIFIER ::= { netbuilderRem 17 } -- nb Rem w/Ae Sw
netbuilderRemAp   OBJECT IDENTIFIER ::= { netbuilderRem 18 } -- nb Rem w/Ap Sw
netbuilderRemAn   OBJECT IDENTIFIER ::= { netbuilderRem 19 } -- nb Rem w/An Sw
netbuilderRemLa   OBJECT IDENTIFIER ::= { netbuilderRem 20 } -- nb Rem w/La Sw
netbuilderRemWa   OBJECT IDENTIFIER ::= { netbuilderRem 21 } -- nb Rem w/Wa Sw
netbuilderRemAa   OBJECT IDENTIFIER ::= { netbuilderRem 22 } -- nb Rem w/Aa Sw
netbuilderRemAb   OBJECT IDENTIFIER ::= { netbuilderRem 23 } -- nb Rem w/Ab Sw
netbuilderRemBf   OBJECT IDENTIFIER ::= { netbuilderRem 24 } -- nb Rem w/Bf Sw

--
-- the following ids are assigned under a3Com.products.brouter.netbuilderRA
--

netbuilderRAbp   OBJECT IDENTIFIER ::= { netbuilderRA 1 }  -- nb RA w/Basic Prot
netbuilderRAcp   OBJECT IDENTIFIER ::= { netbuilderRA 2 }  -- nb RA w/Compl Prot
netbuilderRAxw   OBJECT IDENTIFIER ::= { netbuilderRA 3 }  -- nb RA w/Ext WAN
netbuilderRAcx   OBJECT IDENTIFIER ::= { netbuilderRA 4 }  -- nb RA w/Conn Svc
netbuilderRAba   OBJECT IDENTIFIER ::= { netbuilderRA 5 }  -- nb RA w/Bndry Rtg
netbuilderRAar   OBJECT IDENTIFIER ::= { netbuilderRA 6 }  -- nb RA w/AccRtr SW
netbuilderRAsn   OBJECT IDENTIFIER ::= { netbuilderRA 7 }  -- nb RA w/SNA SW
netbuilderRArb   OBJECT IDENTIFIER ::= { netbuilderRA 8 }  -- nb RA w/RB SW
netbuilderRAff   OBJECT IDENTIFIER ::= { netbuilderRA 9 }  -- nb RA/FF SW
netbuilderRAcf   OBJECT IDENTIFIER ::= { netbuilderRA 10 } -- nb RA w/CF SW
netbuilderRAbx   OBJECT IDENTIFIER ::= { netbuilderRA 11 } -- nb RA w/BX SW
netbuilderRAappn OBJECT IDENTIFIER ::= { netbuilderRA 12 } -- nb RA w/Appn SW
netbuilderRAlm   OBJECT IDENTIFIER ::= { netbuilderRA 13 } -- nb RA w/Lm Sw
netbuilderRAlt   OBJECT IDENTIFIER ::= { netbuilderRA 14 } -- nb RA w/Lt Sw
netbuilderRAwm   OBJECT IDENTIFIER ::= { netbuilderRA 15 } -- nb RA w/Wm Sw
netbuilderRAwt   OBJECT IDENTIFIER ::= { netbuilderRA 16 } -- nb RA w/Wt Sw
netbuilderRAae   OBJECT IDENTIFIER ::= { netbuilderRA 17 } -- nb RA w/Ae Sw
netbuilderRAap   OBJECT IDENTIFIER ::= { netbuilderRA 18 } -- nb RA w/Ap Sw
netbuilderRAan   OBJECT IDENTIFIER ::= { netbuilderRA 19 } -- nb RA w/An Sw
netbuilderRAla   OBJECT IDENTIFIER ::= { netbuilderRA 20 } -- nb RA w/La Sw
netbuilderRAwa   OBJECT IDENTIFIER ::= { netbuilderRA 21 } -- nb RA w/Wa Sw
netbuilderRAaa   OBJECT IDENTIFIER ::= { netbuilderRA 22 } -- nb RA w/Aa Sw
netbuilderRAab   OBJECT IDENTIFIER ::= { netbuilderRA 23 } -- nb RA w/Ab Sw
netbuilderRAbf   OBJECT IDENTIFIER ::= { netbuilderRA 24 } -- nb RA w/Bf Sw

--
-- the following ids are assigned under a3Com.products.brouter.netbuilderRC
--

netbuilderRCbp   OBJECT IDENTIFIER ::= { netbuilderRC 1 }  -- nb RC w/Basic Prot
netbuilderRCcp   OBJECT IDENTIFIER ::= { netbuilderRC 2 }  -- nb RC w/Compl Prot
netbuilderRCxw   OBJECT IDENTIFIER ::= { netbuilderRC 3 }  -- nb RC w/Ext WAN
netbuilderRCcx   OBJECT IDENTIFIER ::= { netbuilderRC 4 }  -- nb RC w/Conn Svc
netbuilderRCba   OBJECT IDENTIFIER ::= { netbuilderRC 5 }  -- nb RC w/Bndry Rtg
netbuilderRCar   OBJECT IDENTIFIER ::= { netbuilderRC 6 }  -- nb RC w/AccRtr SW
netbuilderRCsn   OBJECT IDENTIFIER ::= { netbuilderRC 7 }  -- nb RC w/SNA SW
netbuilderRCrb   OBJECT IDENTIFIER ::= { netbuilderRC 8 }  -- nb RC w/RB SW
netbuilderRCff   OBJECT IDENTIFIER ::= { netbuilderRC 9 }  -- nb RC w/FF SW
netbuilderRCcf   OBJECT IDENTIFIER ::= { netbuilderRC 10 } -- nb RC w/CF SW
netbuilderRCbx   OBJECT IDENTIFIER ::= { netbuilderRC 11 } -- nb RC w/BX SW
netbuilderRCappn OBJECT IDENTIFIER ::= { netbuilderRC 12 } -- nb RC w/Appn SW
netbuilderRClm   OBJECT IDENTIFIER ::= { netbuilderRC 13 } -- nb RC w/Lm Sw
netbuilderRClt   OBJECT IDENTIFIER ::= { netbuilderRC 14 } -- nb RC w/Lt Sw
netbuilderRCwm   OBJECT IDENTIFIER ::= { netbuilderRC 15 } -- nb RC w/Wm Sw
netbuilderRCwt   OBJECT IDENTIFIER ::= { netbuilderRC 16 } -- nb RC w/Wt Sw
netbuilderRCae   OBJECT IDENTIFIER ::= { netbuilderRC 17 } -- nb RC w/Ae Sw
netbuilderRCap   OBJECT IDENTIFIER ::= { netbuilderRC 18 } -- nb RC w/Ap Sw
netbuilderRCan   OBJECT IDENTIFIER ::= { netbuilderRC 19 } -- nb RC w/An Sw
netbuilderRCla   OBJECT IDENTIFIER ::= { netbuilderRC 20 } -- nb RC w/La Sw
netbuilderRCwa   OBJECT IDENTIFIER ::= { netbuilderRC 21 } -- nb RC w/Wa Sw
netbuilderRCaa   OBJECT IDENTIFIER ::= { netbuilderRC 22 } -- nb RC w/Aa Sw
netbuilderRCab   OBJECT IDENTIFIER ::= { netbuilderRC 23 } -- nb RC w/Ab Sw
netbuilderRCbf   OBJECT IDENTIFIER ::= { netbuilderRC 24 } -- nb RC w/Bf Sw

--
-- the following ids are assigned under a3Com.products.brouter.netbuilderTrRem
--

netbuilderTrRemBp   OBJECT IDENTIFIER ::= { netbuilderTrRem 1 }  -- nbtr Rem w/BP
netbuilderTrRemCp   OBJECT IDENTIFIER ::= { netbuilderTrRem 2 }  -- nbtr Rem w/CP
netbuilderTrRemXw   OBJECT IDENTIFIER ::= { netbuilderTrRem 3 }  -- nbtr Rem w/XW
netbuilderTrRemCx   OBJECT IDENTIFIER ::= { netbuilderTrRem 4 }  -- nbtr Rem w/CX
netbuilderTrRemBa   OBJECT IDENTIFIER ::= { netbuilderTrRem 5 }  -- nbtr Rem w/BA
netbuilderTrRemAr   OBJECT IDENTIFIER ::= { netbuilderTrRem 6 }  -- nbtr Rem w/AR
netbuilderTrRemSn   OBJECT IDENTIFIER ::= { netbuilderTrRem 7 }  -- nbtr Rem w/SNA
netbuilderTrRemRb   OBJECT IDENTIFIER ::= { netbuilderTrRem 8 }  -- nb TrRem w/RB
netbuilderTrRemFf   OBJECT IDENTIFIER ::= { netbuilderTrRem 9 }  -- nb TrRem w/FF
netbuilderTrRemCf   OBJECT IDENTIFIER ::= { netbuilderTrRem 10 } -- nb TrRem w/CF
netbuilderTrRemBx   OBJECT IDENTIFIER ::= { netbuilderTrRem 11 } -- nbtr Rem w/BX
netbuilderTrRemAppn OBJECT IDENTIFIER ::= { netbuilderTrRem 12 } -- nb TrRem w/Appn SW  
netbuilderTrRemLm   OBJECT IDENTIFIER ::= { netbuilderTrRem 13 } -- nb TrRem w/Lm  
netbuilderTrRemLt   OBJECT IDENTIFIER ::= { netbuilderTrRem 14 } -- nb TrRem w/Lt  
netbuilderTrRemWm   OBJECT IDENTIFIER ::= { netbuilderTrRem 15 } -- nb TrRem w/Wm
netbuilderTrRemWt   OBJECT IDENTIFIER ::= { netbuilderTrRem 16 } -- nb TrRem w/Wt
netbuilderTrRemAe   OBJECT IDENTIFIER ::= { netbuilderTrRem 17 } -- nb TrRem w/Ae
netbuilderTrRemAp   OBJECT IDENTIFIER ::= { netbuilderTrRem 18 } -- nb TrRem w/Ap
netbuilderTrRemAn   OBJECT IDENTIFIER ::= { netbuilderTrRem 19 } -- nb TrRem w/An
netbuilderTrRemLa   OBJECT IDENTIFIER ::= { netbuilderTrRem 20 } -- nb TrRem w/La
netbuilderTrRemWa   OBJECT IDENTIFIER ::= { netbuilderTrRem 21 } -- nb TrRem w/La
netbuilderTrRemAa   OBJECT IDENTIFIER ::= { netbuilderTrRem 22 } -- nb TrRem w/Aa
netbuilderTrRemAb   OBJECT IDENTIFIER ::= { netbuilderTrRem 23 } -- nb TrRem w/Ab
netbuilderTrRemBf   OBJECT IDENTIFIER ::= { netbuilderTrRem 24 } -- nb TrRem w/Bf


--
-- the following ids are assigned under a3Com.products.brouter.netbuilderTrRC
--

netbuilderTrRCbp   OBJECT IDENTIFIER ::= { netbuilderTrRC 1 }  -- NBTR RC w/Basic Prot
netbuilderTrRCcp   OBJECT IDENTIFIER ::= { netbuilderTrRC 2 }  -- NBTR Rc w/Compl Prot
netbuilderTrRCxw   OBJECT IDENTIFIER ::= { netbuilderTrRC 3 }  -- NBTR Rc w/Ext WAN
netbuilderTrRCcx   OBJECT IDENTIFIER ::= { netbuilderTrRC 4 }  -- NBTR RC w/CX
netbuilderTrRCba   OBJECT IDENTIFIER ::= { netbuilderTrRC 5 }  -- NBTR RC w/BA
netbuilderTrRCar   OBJECT IDENTIFIER ::= { netbuilderTrRC 6 }  -- NBTR RC w/AR
netbuilderTrRCsn   OBJECT IDENTIFIER ::= { netbuilderTrRC 7 }  -- NBTR RC w/SNA
netbuilderTrRCrb   OBJECT IDENTIFIER ::= { netbuilderTrRC 8 }  -- NBTR RC w/RB
netbuilderTrRCff   OBJECT IDENTIFIER ::= { netbuilderTrRC 9 }  -- NBTR RC w/FF
netbuilderTrRCcf   OBJECT IDENTIFIER ::= { netbuilderTrRC 10 } -- NBTR RC w/CF
netbuilderTrRCbx   OBJECT IDENTIFIER ::= { netbuilderTrRC 11 } -- NBTR RC w/BX
netbuilderTrRCappn OBJECT IDENTIFIER ::= { netbuilderTrRC 12 } -- NBTR RC w/Appn SW
netbuilderTrRClm   OBJECT IDENTIFIER ::= { netbuilderTrRC 13 } -- NBTR RC w/Lm
netbuilderTrRClt   OBJECT IDENTIFIER ::= { netbuilderTrRC 14 } -- NBTR RC w/Lt
netbuilderTrRCwm   OBJECT IDENTIFIER ::= { netbuilderTrRC 15 } -- NBTR RC w/Wm
netbuilderTrRCwt   OBJECT IDENTIFIER ::= { netbuilderTrRC 16 } -- NBTR RC w/Wt
netbuilderTrRCae   OBJECT IDENTIFIER ::= { netbuilderTrRC 17 } -- NBTR RC w/Ae
netbuilderTrRCap   OBJECT IDENTIFIER ::= { netbuilderTrRC 18 } -- NBTR RC w/Ap
netbuilderTrRCan   OBJECT IDENTIFIER ::= { netbuilderTrRC 19 } -- NBTR RC w/An
netbuilderTrRCla   OBJECT IDENTIFIER ::= { netbuilderTrRC 20 } -- NBTR RC w/La
netbuilderTrRCwa   OBJECT IDENTIFIER ::= { netbuilderTrRC 21 } -- NBTR RC w/Wa
netbuilderTrRCaa   OBJECT IDENTIFIER ::= { netbuilderTrRC 22 } -- NBTR RC w/Aa
netbuilderTrRCab   OBJECT IDENTIFIER ::= { netbuilderTrRC 23 } -- NBTR RC w/Ab
netbuilderTrRCbf   OBJECT IDENTIFIER ::= { netbuilderTrRC 24 } -- NBTR RC w/Bf

--
-- the following identifiers are assigned under a3Com.products.brouter.nb2_4
--

nb2_4Bp   OBJECT IDENTIFIER ::= { nb2_4 1 }  -- nb2 4 slot w/Basic Prot SW
nb2_4Cp   OBJECT IDENTIFIER ::= { nb2_4 2 }  -- nb2 4 slot w/Compl Prot SW
nb2_4Xw   OBJECT IDENTIFIER ::= { nb2_4 3 }  -- nb2 4 slot w/Ext WAN SW
nb2_4Cx   OBJECT IDENTIFIER ::= { nb2_4 4 }  -- nb2 4 slot w/Conn Svc SW
nb2_4Ba   OBJECT IDENTIFIER ::= { nb2_4 5 }  -- nb2 4 slot w/BA
nb2_4Ar   OBJECT IDENTIFIER ::= { nb2_4 6 }  -- nb2 4 slot w/AR
nb2_4Sn   OBJECT IDENTIFIER ::= { nb2_4 7 }  -- nb2 4 slot w/SNA
nb2_4Rb   OBJECT IDENTIFIER ::= { nb2_4 8 }  -- nb2 4 slot w/RB
nb2_4Ff   OBJECT IDENTIFIER ::= { nb2_4 9 }  -- nb2 4 slot w/Full Feature SW
nb2_4Cf   OBJECT IDENTIFIER ::= { nb2_4 10 } -- nb2 4 slot w/CF
nb2_4Bx   OBJECT IDENTIFIER ::= { nb2_4 11 } -- nb2 4 slot w/BX
nb2_4Appn OBJECT IDENTIFIER ::= { nb2_4 12 } -- nb2 4 slot w/Appn SW
nb2_4Lm   OBJECT IDENTIFIER ::= { nb2_4 13 } -- nb2 4 slot w/Lm Sw
nb2_4Lt   OBJECT IDENTIFIER ::= { nb2_4 14 } -- nb2 4 slot w/Lt Sw
nb2_4Wm   OBJECT IDENTIFIER ::= { nb2_4 15 } -- nb2 4 slot w/Wm Sw
nb2_4Wt   OBJECT IDENTIFIER ::= { nb2_4 16 } -- nb2 4 slot w/Wt Sw
nb2_4Ae   OBJECT IDENTIFIER ::= { nb2_4 17 } -- nb2 4 slot w/Ae Sw
nb2_4Ap   OBJECT IDENTIFIER ::= { nb2_4 18 } -- nb2 4 slot w/Ap Sw
nb2_4An   OBJECT IDENTIFIER ::= { nb2_4 19 } -- nb2 4 slot w/An Sw
nb2_4La   OBJECT IDENTIFIER ::= { nb2_4 20 } -- nb2 4 slot w/La Sw
nb2_4Wa   OBJECT IDENTIFIER ::= { nb2_4 21 } -- nb2 4 slot w/Wa Sw
nb2_4Aa   OBJECT IDENTIFIER ::= { nb2_4 22 } -- nb2 4 slot w/Aa Sw
nb2_4Ab   OBJECT IDENTIFIER ::= { nb2_4 23 } -- nb2 4 slot w/Ab Sw
nb2_4Bf   OBJECT IDENTIFIER ::= { nb2_4 24 } -- nb2 4 slot w/Bf Sw


--
-- the following identifiers are assigned under a3Com.products.brouter.nb2_8
--

nb2_8Bp   OBJECT IDENTIFIER ::= { nb2_8 1 }  -- nb2 8 slot w/Basic Prot SW
nb2_8Cp   OBJECT IDENTIFIER ::= { nb2_8 2 }  -- nb2 8 slot w/Compl Prot SW
nb2_8Xw   OBJECT IDENTIFIER ::= { nb2_8 3 }  -- nb2 8 slot w/Ext WAN SW
nb2_8Cx   OBJECT IDENTIFIER ::= { nb2_8 4 }  -- nb2 8 slot w/Conn Svc SW
nb2_8Ba   OBJECT IDENTIFIER ::= { nb2_8 5 }  -- nb2 8 slot w/BA
nb2_8Ar   OBJECT IDENTIFIER ::= { nb2_8 6 }  -- nb2 8 slot w/AR
nb2_8Sn   OBJECT IDENTIFIER ::= { nb2_8 7 }  -- nb2 8 slot w/SNA
nb2_8Rb   OBJECT IDENTIFIER ::= { nb2_8 8 }  -- nb2 8 slot w/RB
nb2_8Ff   OBJECT IDENTIFIER ::= { nb2_8 9 }  -- nb2 8 slot w/Full Feature SW
nb2_8Cf   OBJECT IDENTIFIER ::= { nb2_8 10 } -- nb2 8 slot w/CF
nb2_8Bx   OBJECT IDENTIFIER ::= { nb2_8 11 } -- nb2 8 slot w/BX
nb2_8Appn OBJECT IDENTIFIER ::= { nb2_8 12 } -- nb2 8 slot w/Appn SW
nb2_8Lm   OBJECT IDENTIFIER ::= { nb2_8 13 } -- nb2 8 slot w/Lm Sw
nb2_8Lt   OBJECT IDENTIFIER ::= { nb2_8 14 } -- nb2 8 slot w/Lt Sw
nb2_8Wm   OBJECT IDENTIFIER ::= { nb2_8 15 } -- nb2 8 slot w/Wm Sw
nb2_8Wt   OBJECT IDENTIFIER ::= { nb2_8 16 } -- nb2 8 slot w/Wt Sw
nb2_8Ae   OBJECT IDENTIFIER ::= { nb2_8 17 } -- nb2 8 slot w/Ae Sw
nb2_8Ap   OBJECT IDENTIFIER ::= { nb2_8 18 } -- nb2 8 slot w/Ap Sw
nb2_8An   OBJECT IDENTIFIER ::= { nb2_8 19 } -- nb2 8 slot w/An Sw
nb2_8La   OBJECT IDENTIFIER ::= { nb2_8 20 } -- nb2 8 slot w/La Sw
nb2_8Wa   OBJECT IDENTIFIER ::= { nb2_8 21 } -- nb2 8 slot w/Wa Sw
nb2_8Aa   OBJECT IDENTIFIER ::= { nb2_8 22 } -- nb2 8 slot w/Aa Sw
nb2_8Ab   OBJECT IDENTIFIER ::= { nb2_8 23 } -- nb2 8 slot w/Ab Sw
nb2_8Bf   OBJECT IDENTIFIER ::= { nb2_8 24 } -- nb2 8 slot w/Bf Sw

--
-- the following identifiers are assigned under a3Com.products.brouter.nbro
--

nbroBp   OBJECT IDENTIFIER ::= { nbro 1 }  -- nbro w/Basic Prot SW
nbroCp   OBJECT IDENTIFIER ::= { nbro 2 }  -- nbro w/Compl Prot SW
nbroXw   OBJECT IDENTIFIER ::= { nbro 3 }  -- nbro w/Ext WAN SW
nbroCx   OBJECT IDENTIFIER ::= { nbro 4 }  -- nbro w/Conn Svc SW
nbro201  OBJECT IDENTIFIER ::= { nbro 5 }  -- nbro w/Bndry Rtg. SW
nbroAr   OBJECT IDENTIFIER ::= { nbro 6 }  -- nbro w/AR
nbroSn   OBJECT IDENTIFIER ::= { nbro 7 }  -- nbro w/SNA
nbro200  OBJECT IDENTIFIER ::= { nbro 8 }  -- nbro w/Bridge Prd. SW
nbroFf   OBJECT IDENTIFIER ::= { nbro 9 }  -- nbro w/Full Feature SW
nbroCf   OBJECT IDENTIFIER ::= { nbro 10 } -- nbro w/CF
nbroBx   OBJECT IDENTIFIER ::= { nbro 11 } -- nbro w/BX
nbroAppn OBJECT IDENTIFIER ::= { nbro 12 } -- nbro w/Appn SW
nbroLm   OBJECT IDENTIFIER ::= { nbro 13 } -- nbro w/Lm Sw
nbroLt   OBJECT IDENTIFIER ::= { nbro 14 } -- nbro w/Lt Sw
nbroWm   OBJECT IDENTIFIER ::= { nbro 15 } -- nbro w/Wm Sw
nbroWt   OBJECT IDENTIFIER ::= { nbro 16 } -- nbro w/Wt Sw
nbroAe   OBJECT IDENTIFIER ::= { nbro 17 } -- nbro w/Ae Sw
nbroAp   OBJECT IDENTIFIER ::= { nbro 18 } -- nbro w/Ap Sw
nbroAn   OBJECT IDENTIFIER ::= { nbro 19 } -- nbro w/An Sw
nbroLa   OBJECT IDENTIFIER ::= { nbro 20 } -- nbro w/La Sw
nbroWa   OBJECT IDENTIFIER ::= { nbro 21 } -- nbro w/Wa Sw
nbro224   OBJECT IDENTIFIER ::= { nbro 22 } -- nbro w/Aa Sw
nbroAb   OBJECT IDENTIFIER ::= { nbro 23 } -- nbro w/Ab Sw
nbro223   OBJECT IDENTIFIER ::= { nbro 24 } -- nbro w/Bf Sw

--
-- the following identifier are assigned under a3Com.products.brouter.netbuilderLocal
--

netbuilderLocalBp   OBJECT IDENTIFIER ::= { netbuilderLocal 1 }  -- nb Local w/BP
netbuilderLocalCp   OBJECT IDENTIFIER ::= { netbuilderLocal 2 }  -- nb Local w/CP
netbuilderLocalXw   OBJECT IDENTIFIER ::= { netbuilderLocal 3 }  -- nb Local w/XW
netbuilderLocalCx   OBJECT IDENTIFIER ::= { netbuilderLocal 4 }  -- nb Local w/CX
netbuilderLocalBa   OBJECT IDENTIFIER ::= { netbuilderLocal 5 }  -- nb Local w/BA
netbuilderLocalAr   OBJECT IDENTIFIER ::= { netbuilderLocal 6 }  -- nb Local w/AR
netbuilderLocalSn   OBJECT IDENTIFIER ::= { netbuilderLocal 7 }  -- nb Local w/SN
netbuilderLocalRb   OBJECT IDENTIFIER ::= { netbuilderLocal 8 }  -- nb Local w/RB
netbuilderLocalFf   OBJECT IDENTIFIER ::= { netbuilderLocal 9 }  -- nb Local w/FF
netbuilderLocalCf   OBJECT IDENTIFIER ::= { netbuilderLocal 10 } -- nb Local w/CF
netbuilderLocalBx   OBJECT IDENTIFIER ::= { netbuilderLocal 11 } -- nb Local w/BX
netbuilderLocalAppn OBJECT IDENTIFIER ::= { netbuilderLocal 12 } -- nb Local w/Appn SW
netbuilderLocalLm   OBJECT IDENTIFIER ::= { netbuilderLocal 13 } -- nb Local w/Lm
netbuilderLocalLt   OBJECT IDENTIFIER ::= { netbuilderLocal 14 } -- nb Local w/Lt
netbuilderLocalWm   OBJECT IDENTIFIER ::= { netbuilderLocal 15 } -- nb Local w/Wm
netbuilderLocalWt   OBJECT IDENTIFIER ::= { netbuilderLocal 16 } -- nb Local w/Wt
netbuilderLocalAe   OBJECT IDENTIFIER ::= { netbuilderLocal 17 } -- nb Local w/Ae
netbuilderLocalAp   OBJECT IDENTIFIER ::= { netbuilderLocal 18 } -- nb Local w/Ap
netbuilderLocalAn   OBJECT IDENTIFIER ::= { netbuilderLocal 19 } -- nb Local w/An
netbuilderLocalLa   OBJECT IDENTIFIER ::= { netbuilderLocal 20 } -- nb Local w/La
netbuilderLocalWa   OBJECT IDENTIFIER ::= { netbuilderLocal 21 } -- nb Local w/Wa
netbuilderLocalAa   OBJECT IDENTIFIER ::= { netbuilderLocal 22 } -- nb Local w/Aa
netbuilderLocalAb   OBJECT IDENTIFIER ::= { netbuilderLocal 23 } -- nb Local w/Ab
netbuilderLocalBf   OBJECT IDENTIFIER ::= { netbuilderLocal 24 } -- nb Local w/Bf


--
-- the following identifiers are assigned under a3Com.products.brouter.netbuilderTrLocal
-- 

netbuilderTrLocalBp   OBJECT IDENTIFIER ::= { netbuilderTrLocal 1 }  -- nbtr Local w/Basic Prot SW
netbuilderTrLocalCp   OBJECT IDENTIFIER ::= { netbuilderTrLocal 2 }  -- nbtr Local w/Compl Prot SW
netbuilderTrLocalXw   OBJECT IDENTIFIER ::= { netbuilderTrLocal 3 }  -- nbtr Local w/XW
netbuilderTrLocalCx   OBJECT IDENTIFIER ::= { netbuilderTrLocal 4 }  -- nbtr Local w/CX
netbuilderTrLocalBa   OBJECT IDENTIFIER ::= { netbuilderTrLocal 5 }  -- nbtr Local w/BA
netbuilderTrLocalAr   OBJECT IDENTIFIER ::= { netbuilderTrLocal 6 }  -- nbtr Local w/Acc Rtr SW
netbuilderTrLocalSn   OBJECT IDENTIFIER ::= { netbuilderTrLocal 7 }  -- nbtr Local w/SNA Acc Rtr SW
netbuilderTrLocalRb   OBJECT IDENTIFIER ::= { netbuilderTrLocal 8 }  -- nbtr Local w/RB
netbuilderTrLocalFf   OBJECT IDENTIFIER ::= { netbuilderTrLocal 9 }  -- nbtr Local w/FF
netbuilderTrLocalCf   OBJECT IDENTIFIER ::= { netbuilderTrLocal 10 } -- nbtr Local w/CF
netbuilderTrLocalBx   OBJECT IDENTIFIER ::= { netbuilderTrLocal 11 } -- nbtr Local w/BX SW
netbuilderTrLocalAppn OBJECT IDENTIFIER ::= { netbuilderTrLocal 12 } -- nb TrLocal w/Appn SW
netbuilderTrLocalLm   OBJECT IDENTIFIER ::= { netbuilderTrLocal 13 } -- nbtr Local w/Lm
netbuilderTrLocalLt   OBJECT IDENTIFIER ::= { netbuilderTrLocal 14 } -- nbtr Local w/Lt
netbuilderTrLocalWm   OBJECT IDENTIFIER ::= { netbuilderTrLocal 15 } -- nbtr Local w/Wm
netbuilderTrLocalWt   OBJECT IDENTIFIER ::= { netbuilderTrLocal 16 } -- nbtr Local w/Wt
netbuilderTrLocalAe   OBJECT IDENTIFIER ::= { netbuilderTrLocal 17 } -- nbtr Local w/Ae
netbuilderTrLocalAp   OBJECT IDENTIFIER ::= { netbuilderTrLocal 18 } -- nbtr Local w/Ap
netbuilderTrLocalAn   OBJECT IDENTIFIER ::= { netbuilderTrLocal 19 } -- nbtr Local w/An
netbuilderTrLocalLa   OBJECT IDENTIFIER ::= { netbuilderTrLocal 20 } -- nbtr Local w/La
netbuilderTrLocalWa   OBJECT IDENTIFIER ::= { netbuilderTrLocal 21 } -- nbtr Local w/Wa
netbuilderTrLocalAa   OBJECT IDENTIFIER ::= { netbuilderTrLocal 22 } -- nbtr Local w/Aa
netbuilderTrLocalAb   OBJECT IDENTIFIER ::= { netbuilderTrLocal 23 } -- nbtr Local w/Ab
netbuilderTrLocalBf   OBJECT IDENTIFIER ::= { netbuilderTrLocal 24 } -- nbtr Local w/Bf

--
-- the following identifiers are assigned under a3Com.products.brouter.netbuilderRC1x2
--

netbuilderRC1x2bp   OBJECT IDENTIFIER ::= { netbuilderRC1x2 1 }  -- nbRC1x2 w/BP
netbuilderRC1x2cp   OBJECT IDENTIFIER ::= { netbuilderRC1x2 2 }  -- nbRC1x2 w/CP
netbuilderRC1x2xw   OBJECT IDENTIFIER ::= { netbuilderRC1x2 3 }  -- nbRC1x2 w/XW
netbuilderRC1x2cx   OBJECT IDENTIFIER ::= { netbuilderRC1x2 4 }  -- nbRC1x2 w/CX
netbuilderRC1x2ba   OBJECT IDENTIFIER ::= { netbuilderRC1x2 5 }  -- nbRC1x2 w/BA
netbuilderRC1x2ar   OBJECT IDENTIFIER ::= { netbuilderRC1x2 6 }  -- nb RC1x2 w/AR
netbuilderRC1x2sn   OBJECT IDENTIFIER ::= { netbuilderRC1x2 7 }  -- nb RC1x2 w/SN
netbuilderRC1x2rb   OBJECT IDENTIFIER ::= { netbuilderRC1x2 8 }  -- nb RC1x2 w/RB
netbuilderRC1x2ff   OBJECT IDENTIFIER ::= { netbuilderRC1x2 9 }  -- nb RC1x2 w/FF
netbuilderRC1x2cf   OBJECT IDENTIFIER ::= { netbuilderRC1x2 10 } -- nb RC1x2 w/CF
netbuilderRC1x2bx   OBJECT IDENTIFIER ::= { netbuilderRC1x2 11 } -- nb RC1x2 w/BX
netbuilderRC1x2appn OBJECT IDENTIFIER ::= { netbuilderRC1x2 12 } -- RC1x2 w/Appn
netbuilderRC1x2lm   OBJECT IDENTIFIER ::= { netbuilderRC1x2 13 } -- RC1x2 w/Lm 
netbuilderRC1x2lt   OBJECT IDENTIFIER ::= { netbuilderRC1x2 14 } -- RC1x2 w/Lt Sw
netbuilderRC1x2wm   OBJECT IDENTIFIER ::= { netbuilderRC1x2 15 } -- RC1x2 w/Wm Sw
netbuilderRC1x2wt   OBJECT IDENTIFIER ::= { netbuilderRC1x2 16 } -- RC1x2 w/Wt Sw
netbuilderRC1x2ae   OBJECT IDENTIFIER ::= { netbuilderRC1x2 17 } -- RC1x2 w/Ae Sw
netbuilderRC1x2ap   OBJECT IDENTIFIER ::= { netbuilderRC1x2 18 } -- RC1x2 w/Ap Sw
netbuilderRC1x2an   OBJECT IDENTIFIER ::= { netbuilderRC1x2 19 } -- RC1x2 w/An Sw
netbuilderRC1x2la   OBJECT IDENTIFIER ::= { netbuilderRC1x2 20 } -- RC1x2 w/La Sw
netbuilderRC1x2wa   OBJECT IDENTIFIER ::= { netbuilderRC1x2 21 } -- RC1x2 w/Wa Sw
netbuilderRC1x2aa   OBJECT IDENTIFIER ::= { netbuilderRC1x2 22 } -- RC1x2 w/Aa Sw
netbuilderRC1x2ab   OBJECT IDENTIFIER ::= { netbuilderRC1x2 23 } -- RC1x2 w/Ab Sw
netbuilderRC1x2bf   OBJECT IDENTIFIER ::= { netbuilderRC1x2 24 } -- RC1x2 w/Bf Sw

--
-- the following identifiers are assigned under a3Com.products.brouter.netbuilderTrRC1x2
--

netbuilderTrRC1x2bp   OBJECT IDENTIFIER ::= { netbuilderTrRC1x2 1 }
netbuilderTrRC1x2cp   OBJECT IDENTIFIER ::= { netbuilderTrRC1x2 2 }
netbuilderTrRC1x2xw   OBJECT IDENTIFIER ::= { netbuilderTrRC1x2 3 }
netbuilderTrRC1x2cx   OBJECT IDENTIFIER ::= { netbuilderTrRC1x2 4 }
netbuilderTrRC1x2ba   OBJECT IDENTIFIER ::= { netbuilderTrRC1x2 5 }
netbuilderTrRC1x2ar   OBJECT IDENTIFIER ::= { netbuilderTrRC1x2 6 }
netbuilderTrRC1x2sn   OBJECT IDENTIFIER ::= { netbuilderTrRC1x2 7 }
netbuilderTrRC1x2rb   OBJECT IDENTIFIER ::= { netbuilderTrRC1x2 8 }
netbuilderTrRC1x2ff   OBJECT IDENTIFIER ::= { netbuilderTrRC1x2 9 }
netbuilderTrRC1x2cf   OBJECT IDENTIFIER ::= { netbuilderTrRC1x2 10 }
netbuilderTrRC1x2bx   OBJECT IDENTIFIER ::= { netbuilderTrRC1x2 11 }
netbuilderTrRC1x2appn OBJECT IDENTIFIER ::= { netbuilderTrRC1x2 12 }
netbuilderTrRC1x2lm   OBJECT IDENTIFIER ::= { netbuilderTrRC1x2 13 }
netbuilderTrRC1x2lt   OBJECT IDENTIFIER ::= { netbuilderTrRC1x2 14 }
netbuilderTrRC1x2wm   OBJECT IDENTIFIER ::= { netbuilderTrRC1x2 15 }
netbuilderTrRC1x2wt   OBJECT IDENTIFIER ::= { netbuilderTrRC1x2 16 }
netbuilderTrRC1x2ae   OBJECT IDENTIFIER ::= { netbuilderTrRC1x2 17 }
netbuilderTrRC1x2ap   OBJECT IDENTIFIER ::= { netbuilderTrRC1x2 18 }
netbuilderTrRC1x2an   OBJECT IDENTIFIER ::= { netbuilderTrRC1x2 19 }
netbuilderTrRC1x2la   OBJECT IDENTIFIER ::= { netbuilderTrRC1x2 20 }
netbuilderTrRC1x2wa   OBJECT IDENTIFIER ::= { netbuilderTrRC1x2 21 }
netbuilderTrRC1x2aa   OBJECT IDENTIFIER ::= { netbuilderTrRC1x2 22 }
netbuilderTrRC1x2ab   OBJECT IDENTIFIER ::= { netbuilderTrRC1x2 23 }
netbuilderTrRC1x2bf   OBJECT IDENTIFIER ::= { netbuilderTrRC1x2 24 }

--
-- the following identifiers are assigned under a3Com.products.brouter.casper
-- (casper aka "nbro Large" )
--

nbrolBp   OBJECT IDENTIFIER ::= { casper 1 }  -- casper w/Basic Prot SW
nbrolCp   OBJECT IDENTIFIER ::= { casper 2 }  -- casper w/Compl Prot SW
nbrolXw   OBJECT IDENTIFIER ::= { casper 3 }  -- casper w/Ext WAN SW
nbrol228   OBJECT IDENTIFIER ::= { casper 4 }  -- casper w/Conn Svc SW
nbrol201  OBJECT IDENTIFIER ::= { casper 5 }  -- casper w/Bndry Rtg. SW
nbro222   OBJECT IDENTIFIER ::= { casper 6 }  -- casper w/AR SW
nbrolSn   OBJECT IDENTIFIER ::= { casper 7 }  -- casper w/SNA
nbrol200  OBJECT IDENTIFIER ::= { casper 8 }  -- casper w/RB. SW
nbrolFf   OBJECT IDENTIFIER ::= { casper 9 }  -- casper w/Full Feature SW
nbro227   OBJECT IDENTIFIER ::= { casper 10 } -- casper w/CF SW
nbro221   OBJECT IDENTIFIER ::= { casper 11 } -- casper w/BX SW
nbrolAppn OBJECT IDENTIFIER ::= { casper 12 } -- casper w/Appn SW
nbrolLm   OBJECT IDENTIFIER ::= { casper 13 } -- casper w/Lm Sw
nbrolLt   OBJECT IDENTIFIER ::= { casper 14 } -- casper w/Lt Sw
nbrolWm   OBJECT IDENTIFIER ::= { casper 15 } -- casper w/Wm Sw
nbrolWt   OBJECT IDENTIFIER ::= { casper 16 } -- casper w/Wt Sw
nbrolAe   OBJECT IDENTIFIER ::= { casper 17 } -- casper w/Ae Sw
nbrolAp   OBJECT IDENTIFIER ::= { casper 18 } -- casper w/Ap Sw
nbrolAn   OBJECT IDENTIFIER ::= { casper 19 } -- casper w/An Sw
nbrolLa   OBJECT IDENTIFIER ::= { casper 20 } -- casper w/La Sw
nbrolWa   OBJECT IDENTIFIER ::= { casper 21 } -- casper w/Wa Sw
nbrol224   OBJECT IDENTIFIER ::= { casper 22 } -- casper w/Aa Sw
nbrolAb   OBJECT IDENTIFIER ::= { casper 23 } -- casper w/Ab Sw
nbrol223   OBJECT IDENTIFIER ::= { casper 24 } -- casper w/Bf Sw

--
-- the following identifiers are assigned under a3Com.products.brouter.spectreHuge
-- (spectre Huge aka nbro Huge )
--

nbrohBp   OBJECT IDENTIFIER ::= { spectreHuge 1 }  -- spectreHuge w/BP SW
nbrohCp   OBJECT IDENTIFIER ::= { spectreHuge 2 }  -- spectreHuge w/CP SW
nbrohXw   OBJECT IDENTIFIER ::= { spectreHuge 3 }  -- spectreHuge w/Ext WAN SW
nbro228   OBJECT IDENTIFIER ::= { spectreHuge 4 }  -- spectreHuge w/CX SW
nbroh201  OBJECT IDENTIFIER ::= { spectreHuge 5 }  -- casper w/Bndry Rtg. SW
nbroh222  OBJECT IDENTIFIER ::= { spectreHuge 6 }  -- spectreHuge w/AR SW
nbrohSn   OBJECT IDENTIFIER ::= { spectreHuge 7 }  -- spectreHuge w/SNA
nbroh200  OBJECT IDENTIFIER ::= { spectreHuge 8 }  -- spectreHuge w/RB SW
nbrohFf   OBJECT IDENTIFIER ::= { spectreHuge 9 }  -- spectreHuge w/FF SW
nbroh227  OBJECT IDENTIFIER ::= { spectreHuge 10 } -- spectreHuge w/CF SW
nbroh221  OBJECT IDENTIFIER ::= { spectreHuge 11 } -- spectreHuge w/BX SW
nbrohAppn OBJECT IDENTIFIER ::= { spectreHuge 12 } -- spectreHuge w/Appn SW
nbrohLm   OBJECT IDENTIFIER ::= { spectreHuge 13 } -- spectreHuge w/Lm Sw
nbrohLt   OBJECT IDENTIFIER ::= { spectreHuge 14 } -- spectreHuge w/Lt Sw
nbrohWm   OBJECT IDENTIFIER ::= { spectreHuge 15 } -- spectreHuge w/Wm Sw
nbrohWt   OBJECT IDENTIFIER ::= { spectreHuge 16 } -- spectreHuge w/Wt Sw
nbrohAe   OBJECT IDENTIFIER ::= { spectreHuge 17 } -- spectreHuge w/Ae Sw
nbrohAp   OBJECT IDENTIFIER ::= { spectreHuge 18 } -- spectreHuge w/Ap Sw
nbrohAn   OBJECT IDENTIFIER ::= { spectreHuge 19 } -- spectreHuge w/An Sw
nbrohLa   OBJECT IDENTIFIER ::= { spectreHuge 20 } -- spectreHuge w/La Sw
nbrohWa   OBJECT IDENTIFIER ::= { spectreHuge 21 } -- spectreHuge w/Wa Sw
nbroh224   OBJECT IDENTIFIER ::= { spectreHuge 22 } -- spectreHuge w/Aa Sw
nbrohAb   OBJECT IDENTIFIER ::= { spectreHuge 23 } -- spectreHuge w/Ab Sw
nbroh223   OBJECT IDENTIFIER ::= { spectreHuge 24 } -- spectreHuge w/Bf Sw

--
-- the following identifiers are assigned under a3Com.products.brouter.spectreIsdn
--

nbroiBp   OBJECT IDENTIFIER ::= { spectreIsdn 1 }  -- spectreIsdn w/BP SW
nbroiCp   OBJECT IDENTIFIER ::= { spectreIsdn 2 }  -- spectreIsdn w/CP SW
nbroiXw   OBJECT IDENTIFIER ::= { spectreIsdn 3 }  -- spectreIsdn w/Ext WAN SW
nbroiCX  OBJECT IDENTIFIER ::= { spectreIsdn 4 }  -- spectreIsdn w/CX SW
nbroiBA  OBJECT IDENTIFIER ::= { spectreIsdn 5 }  -- spectreIsdn w/Bndry Rtg. SW
nbro422   OBJECT IDENTIFIER ::= { spectreIsdn 6 }  -- spectreIsdn w/AR SW
nbroiSn   OBJECT IDENTIFIER ::= { spectreIsdn 7 }  -- spectreIsdn w/SNA
nbroi200  OBJECT IDENTIFIER ::= { spectreIsdn 8 }  -- spectreIsdn w/RB SW
nbroiFf   OBJECT IDENTIFIER ::= { spectreIsdn 9 }  -- spectreIsdn w/FF SW
nbroil427 OBJECT IDENTIFIER ::= { spectreIsdn 10 } -- spectreIsdn w/CF SW
nbro421   OBJECT IDENTIFIER ::= { spectreIsdn 11 } -- spectreIsdn w/BX SW
nbroiAppn OBJECT IDENTIFIER ::= { spectreIsdn 12 } -- spectreIsdn w/Appn SW
nbroiLm   OBJECT IDENTIFIER ::= { spectreIsdn 13 } -- spectreIsdn w/Lm Sw
nbroiLt   OBJECT IDENTIFIER ::= { spectreIsdn 14 } -- spectreIsdn w/Lt Sw
nbroiWm   OBJECT IDENTIFIER ::= { spectreIsdn 15 } -- spectreIsdn w/Wm Sw
nbroiWt   OBJECT IDENTIFIER ::= { spectreIsdn 16 } -- spectreIsdn w/Wt Sw
nbroiAe   OBJECT IDENTIFIER ::= { spectreIsdn 17 } -- spectreIsdn w/Ae Sw
nbroiAp   OBJECT IDENTIFIER ::= { spectreIsdn 18 } -- spectreIsdn w/Ap Sw
nbroiAn   OBJECT IDENTIFIER ::= { spectreIsdn 19 } -- spectreIsdn w/An Sw
nbroiLa   OBJECT IDENTIFIER ::= { spectreIsdn 20 } -- spectreIsdn w/La Sw
nbroiWa   OBJECT IDENTIFIER ::= { spectreIsdn 21 } -- spectreIsdn w/Wa Sw
nbroi424   OBJECT IDENTIFIER ::= { spectreIsdn 22 } -- spectreIsdn w/Aa Sw
nbroiAb   OBJECT IDENTIFIER ::= { spectreIsdn 23 } -- spectreIsdn w/Ab Sw
nbroi423   OBJECT IDENTIFIER ::= { spectreIsdn 24 } -- spectreIsdn w/Bf Sw

--
-- the following identifiers are assigned under a3Com.products.brouter.nb2_8_4fddi
--

nb2_8_4fddiBp   OBJECT IDENTIFIER ::= { nb2_8_4fddi 1 }  -- crew 4fddi w/BP
nb2_8_4fddiCp   OBJECT IDENTIFIER ::= { nb2_8_4fddi 2 }  -- crew 4fddi w/CP
nb2_8_4fddiXw   OBJECT IDENTIFIER ::= { nb2_8_4fddi 3 }  -- crew 4fddi w/XW
nb2_8_4fddiCx   OBJECT IDENTIFIER ::= { nb2_8_4fddi 4 }  -- crew 4fddi w/CX
nb2_8_4fddiBa   OBJECT IDENTIFIER ::= { nb2_8_4fddi 5 }  -- crew 4fddi w/BA
nb2_8_4fddiAr   OBJECT IDENTIFIER ::= { nb2_8_4fddi 6 }  -- crew 4fddi w/AR
nb2_8_4fddiSn   OBJECT IDENTIFIER ::= { nb2_8_4fddi 7 }  -- crew 4fddi w/SNA
nb2_8_4fddiRb   OBJECT IDENTIFIER ::= { nb2_8_4fddi 8 }  -- crew 4fddi w/RB
nb2_8_4fddiFf   OBJECT IDENTIFIER ::= { nb2_8_4fddi 9 }  -- crew 4fddi w/FF
nb2_8_4fddiCf   OBJECT IDENTIFIER ::= { nb2_8_4fddi 10 } -- crew 4fddi w/CF
nb2_8_4fddiBx   OBJECT IDENTIFIER ::= { nb2_8_4fddi 11 } -- crew 4fddi w/BX
nb2_8_4fddiAppn OBJECT IDENTIFIER ::= { nb2_8_4fddi 12 } -- crew 4fddi w/Appn
nb2_8_4fddiLm   OBJECT IDENTIFIER ::= { nb2_8_4fddi 13 } -- crew 4fddi w/Lm
nb2_8_4fddiLt   OBJECT IDENTIFIER ::= { nb2_8_4fddi 14 } -- crew 4fddi w/Lt
nb2_8_4fddiWm   OBJECT IDENTIFIER ::= { nb2_8_4fddi 15 } -- crew 4fddi w/Wm
nb2_8_4fddiWt   OBJECT IDENTIFIER ::= { nb2_8_4fddi 16 } -- crew 4fddi w/Wt
nb2_8_4fddiAe   OBJECT IDENTIFIER ::= { nb2_8_4fddi 17 } -- crew 4fddi w/Ae
nb2_8_4fddiAp   OBJECT IDENTIFIER ::= { nb2_8_4fddi 18 } -- crew 4fddi w/Ap
nb2_8_4fddiAn   OBJECT IDENTIFIER ::= { nb2_8_4fddi 19 } -- crew 4fddi w/An
nb2_8_4fddiLa   OBJECT IDENTIFIER ::= { nb2_8_4fddi 20 } -- crew 4fddi w/La
nb2_8_4fddiWa   OBJECT IDENTIFIER ::= { nb2_8_4fddi 21 } -- crew 4fddi w/Wa
nb2_8_4fddiAa   OBJECT IDENTIFIER ::= { nb2_8_4fddi 22 } -- crew 4fddi w/Aa
nb2_8_4fddiAb   OBJECT IDENTIFIER ::= { nb2_8_4fddi 23 } -- crew 4fddi w/Ab
nb2_8_4fddiBf   OBJECT IDENTIFIER ::= { nb2_8_4fddi 24 } -- crew 4fddi w/Bf

--
-- the following identifiers are assigned under a3Com.products.brouter.nb2_8_dualwide
--

nb2_8_dualwideBp   OBJECT IDENTIFIER ::= { nb2_8_dualwide 1 }  -- crew dualwide w/BP
nb2_8_dualwideCp   OBJECT IDENTIFIER ::= { nb2_8_dualwide 2 }  -- crew dualwide w/CP
nb2_8_dualwideXw   OBJECT IDENTIFIER ::= { nb2_8_dualwide 3 }  -- crew dualwide w/XW
nb2_8_dualwideCx   OBJECT IDENTIFIER ::= { nb2_8_dualwide 4 }  -- crew dualwide w/CX
nb2_8_dualwideBa   OBJECT IDENTIFIER ::= { nb2_8_dualwide 5 }  -- crew dualwide w/BA
nb2_8_dualwideAr   OBJECT IDENTIFIER ::= { nb2_8_dualwide 6 }  -- crew dualwide w/AR
nb2_8_dualwideSn   OBJECT IDENTIFIER ::= { nb2_8_dualwide 7 }  -- crew dualwide w/SNA
nb2_8_dualwideRb   OBJECT IDENTIFIER ::= { nb2_8_dualwide 8 }  -- crew dualwide w/RB
nb2_8_dualwideFf   OBJECT IDENTIFIER ::= { nb2_8_dualwide 9 }  -- crew dualwide w/FF
nb2_8_dualwideCf   OBJECT IDENTIFIER ::= { nb2_8_dualwide 10 } -- crew dualwide w/CF
nb2_8_dualwideBx   OBJECT IDENTIFIER ::= { nb2_8_dualwide 11 } -- crew dualwide w/BX
nb2_8_dualwideAppn OBJECT IDENTIFIER ::= { nb2_8_dualwide 12 } -- crew dualwide w/Appn
nb2_8_dualwideLm   OBJECT IDENTIFIER ::= { nb2_8_dualwide 13 } -- crew dualwide w/Lm
nb2_8_dualwideLt   OBJECT IDENTIFIER ::= { nb2_8_dualwide 14 } -- crew dualwide w/Lt
nb2_8_dualwideWm   OBJECT IDENTIFIER ::= { nb2_8_dualwide 15 } -- crew dualwide w/Wm
nb2_8_dualwideWt   OBJECT IDENTIFIER ::= { nb2_8_dualwide 16 } -- crew dualwide w/Wt
nb2_8_dualwideAe   OBJECT IDENTIFIER ::= { nb2_8_dualwide 17 } -- crew dualwide w/Ae
nb2_8_dualwideAp   OBJECT IDENTIFIER ::= { nb2_8_dualwide 18 } -- crew dualwide w/Ap
nb2_8_dualwideAn   OBJECT IDENTIFIER ::= { nb2_8_dualwide 19 } -- crew dualwide w/An
nb2_8_dualwideLa   OBJECT IDENTIFIER ::= { nb2_8_dualwide 20 } -- crew dualwide w/La
nb2_8_dualwideWa   OBJECT IDENTIFIER ::= { nb2_8_dualwide 21 } -- crew dualwide w/Wa
nb2_8_dualwideAa   OBJECT IDENTIFIER ::= { nb2_8_dualwide 22 } -- crew dualwide w/Aa
nb2_8_dualwideAb   OBJECT IDENTIFIER ::= { nb2_8_dualwide 23 } -- crew dualwide w/Ab
nb2_8_dualwideBf   OBJECT IDENTIFIER ::= { nb2_8_dualwide 24 } -- crew dualwide w/Bf

--
-- the following identifiers are assigned under a3Com.products.brouter.spectreIs dnHuge
--

nbroihBp  OBJECT IDENTIFIER ::= { spectreIsdnHuge 1 } --spectreIsdn w/BP SW
nbroihCp  OBJECT IDENTIFIER ::= { spectreIsdnHuge 2 } --spectreIsdn w/CP SW
nbroihXw  OBJECT IDENTIFIER ::= { spectreIsdnHuge 3 } -- spectreIsdn w/Ext WAN SW
nbroihCx OBJECT IDENTIFIER ::= { spectreIsdnHuge 4 } -- spectreIsdn w/CX SW
nbroihBa OBJECT IDENTIFIER ::= { spectreIsdnHuge 5 } --spectreIsdn w/Bndry Rtg . SW
nbroih422  OBJECT IDENTIFIER ::= { spectreIsdnHuge 6 } --spectreIsdn w/AR SW
nbroihSn  OBJECT IDENTIFIER ::= { spectreIsdnHuge 7 } --spectreIsdn w/SNA
nbroihRb OBJECT IDENTIFIER ::= { spectreIsdnHuge 8 } --spectreIsdn w/RB SW
nbroihFf  OBJECT IDENTIFIER ::= { spectreIsdnHuge 9 } -- spectreIsdn w/FF SW
nbroih427  OBJECT IDENTIFIER ::= { spectreIsdnHuge 10 }--spectreIsdn w/CF SW
nbroih421  OBJECT IDENTIFIER ::= { spectreIsdnHuge 11 }--spectreIsdn w/BX SW
nbroihAppn OBJECT IDENTIFIER ::= { spectreIsdnHuge 12 } -- spectreIsdn w/Appn
nbroihLm OBJECT IDENTIFIER ::= { spectreIsdnHuge 13 } -- spectreIsdn w/Lm Sw
nbroihLt OBJECT IDENTIFIER ::= { spectreIsdnHuge 14 } -- spectreIsdn w/Lt Sw
nbroihWm OBJECT IDENTIFIER ::= { spectreIsdnHuge 15 } -- spectreIsdn w/Wm Sw
nbroihWt OBJECT IDENTIFIER ::= { spectreIsdnHuge 16 } -- spectreIsdn w/Wt Sw
nbroihAe OBJECT IDENTIFIER ::= { spectreIsdnHuge 17 } -- spectreIsdn w/Ae Sw
nbroihAp OBJECT IDENTIFIER ::= { spectreIsdnHuge 18 } -- spectreIsdn w/Ap Sw
nbroihAn OBJECT IDENTIFIER ::= { spectreIsdnHuge 19 } -- spectreIsdn w/An Sw
nbroihLa OBJECT IDENTIFIER ::= { spectreIsdnHuge 20 } -- spectreIsdn w/La Sw
nbroihWa OBJECT IDENTIFIER ::= { spectreIsdnHuge 21 } -- spectreIsdn w/Wa Sw
nbroih424 OBJECT IDENTIFIER ::= { spectreIsdnHuge 22 } -- spectreIsdn w/Aa Sw
nbroihAb OBJECT IDENTIFIER ::= { spectreIsdnHuge 23 } -- spectreIsdn w/Ab Sw
nbroih423 OBJECT IDENTIFIER ::= { spectreIsdnHuge 24 } -- spectreIsdn w/Bf Sw

--
-- the following identifiers are assigned under a3Com.products.brouter.nbroTrLarge
--

nbroTrlBp  OBJECT IDENTIFIER ::= { nbroTrLarge 1 } --nbroTrLarge w/BP SW
nbroTrlCp  OBJECT IDENTIFIER ::= { nbroTrLarge 2 } --nbroTrLarge w/CP SW
nbroTrlXw  OBJECT IDENTIFIER ::= { nbroTrLarge 3 } -- nbroTrLarge w/Ext WAN SW
nbroTrlCx OBJECT IDENTIFIER ::= { nbroTrLarge 4 } -- nbroTrLarge w/CX SW
nbroTrlBa OBJECT IDENTIFIER ::= { nbroTrLarge 5 } --nbroTrLarge w/Bndry Rtg. SW
nbro322  OBJECT IDENTIFIER ::= { nbroTrLarge 6 } --nbroTrLarge w/AR SW
nbroTrlSn  OBJECT IDENTIFIER ::= { nbroTrLarge 7 } --nbroTrLarge w/SNA
nbroTrlRb OBJECT IDENTIFIER ::= { nbroTrLarge 8 } --nbroTrLarge w/RB SW
nbroTrlFf  OBJECT IDENTIFIER ::= { nbroTrLarge 9 } -- nbroTrLarge w/FF SW
nbroTrl327  OBJECT IDENTIFIER ::= { nbroTrLarge 10 }--nbroTrLarge w/CF SW
nbro321     OBJECT IDENTIFIER ::= { nbroTrLarge 11 }--nbroTrLarge w/BX SW
nbroTrlAppn OBJECT IDENTIFIER ::= { nbroTrLarge 12 } -- nbroTrLarge w/Appn SW
nbroTrlLm OBJECT IDENTIFIER ::= { nbroTrLarge 13 } -- nbroTrLarge w/Lm Sw
nbroTrlLt OBJECT IDENTIFIER ::= { nbroTrLarge 14 } -- nbroTrLarge w/Lt Sw
nbroTrlWm OBJECT IDENTIFIER ::= { nbroTrLarge 15 } -- nbroTrLarge w/Wm Sw
nbroTrlWt OBJECT IDENTIFIER ::= { nbroTrLarge 16 } -- nbroTrLarge w/Wt Sw
nbroTrlAe OBJECT IDENTIFIER ::= { nbroTrLarge 17 } -- nbroTrLarge w/Ae Sw
nbroTrlAp OBJECT IDENTIFIER ::= { nbroTrLarge 18 } -- nbroTrLarge w/Ap Sw
nbroTrlAn OBJECT IDENTIFIER ::= { nbroTrLarge 19 } -- nbroTrLarge w/An Sw
nbroTrlLa OBJECT IDENTIFIER ::= { nbroTrLarge 20 } -- nbroTrLarge w/La Sw
nbroTrlWa OBJECT IDENTIFIER ::= { nbroTrLarge 21 } -- nbroTrLarge w/Wa Sw
nbroTrlAa OBJECT IDENTIFIER ::= { nbroTrLarge 22 } -- nbroTrLarge w/Aa Sw
nbroTrlAb OBJECT IDENTIFIER ::= { nbroTrLarge 23 } -- nbroTrLarge w/Ab Sw
nbroTrl323 OBJECT IDENTIFIER ::= { nbroTrLarge 24 } -- nbroTrLarge w/Bf Sw


--
-- the following identifiers are assigned under a3Com.products.brouter.nbroTrIsdn
--

nbroTrIsdnBp  OBJECT IDENTIFIER ::= { nbroTrIsdn 1 } --nbroTrIsdn w/BP SW
nbroTrIsdnCp  OBJECT IDENTIFIER ::= { nbroTrIsdn 2 } --nbroTrIsdn w/CP SW
nbroTrIsdnXw  OBJECT IDENTIFIER ::= { nbroTrIsdn 3 } -- nbroTrIsdn w/Ext WAN SW
nbroTrIsdnCx OBJECT IDENTIFIER ::= { nbroTrIsdn 4 } -- nbroTrIsdn w/CX SW
nbroTrIsdnBa OBJECT IDENTIFIER ::= { nbroTrIsdn 5 } --nbroTrIsdn w/Bndry Rtg. SW
nbroTrIsdnAr  OBJECT IDENTIFIER ::= { nbroTrIsdn 6 } --nbroTrIsdn w/AR SW
nbroTrIsdnSn  OBJECT IDENTIFIER ::= { nbroTrIsdn 7 } --nbroTrIsdn w/SNA
nbroTrIsdnRb OBJECT IDENTIFIER ::= { nbroTrIsdn 8 } --nbroTrIsdn w/RB SW
nbroTrIsdnFf  OBJECT IDENTIFIER ::= { nbroTrIsdn 9 } -- nbroTrIsdn w/FF SW
nbro527  OBJECT IDENTIFIER ::= { nbroTrIsdn 10 }--nbroTrIsdn w/CF SW
nbroTrIsdnBx     OBJECT IDENTIFIER ::= { nbroTrIsdn 11 }--nbroTrIsdn w/BX SW
nbroTrIsdnAppn OBJECT IDENTIFIER ::= { nbroTrIsdn 12 } -- nbroTrIsdn w/Appn SW
nbroTrIsdnLm OBJECT IDENTIFIER ::= { nbroTrIsdn 13 } -- nbroTrIsdn w/Lm Sw
nbroTrIsdnLt OBJECT IDENTIFIER ::= { nbroTrIsdn 14 } -- nbroTrIsdn w/Lt Sw
nbroTrIsdnWm OBJECT IDENTIFIER ::= { nbroTrIsdn 15 } -- nbroTrIsdn w/Wm Sw
nbroTrIsdnWt OBJECT IDENTIFIER ::= { nbroTrIsdn 16 } -- nbroTrIsdn w/Wt Sw
nbroTrIsdnAe OBJECT IDENTIFIER ::= { nbroTrIsdn 17 } -- nbroTrIsdn w/Ae Sw
nbroTrIsdnAp OBJECT IDENTIFIER ::= { nbroTrIsdn 18 } -- nbroTrIsdn w/Ap Sw
nbroTrIsdnAn OBJECT IDENTIFIER ::= { nbroTrIsdn 19 } -- nbroTrIsdn w/An Sw
nbroTrIsdnLa OBJECT IDENTIFIER ::= { nbroTrIsdn 20 } -- nbroTrIsdn w/La Sw
nbroTrIsdnWa OBJECT IDENTIFIER ::= { nbroTrIsdn 21 } -- nbroTrIsdn w/Wa Sw
nbroTrIsdnAa OBJECT IDENTIFIER ::= { nbroTrIsdn 22 } -- nbroTrIsdn w/Aa Sw
nbroTrIsdnAb OBJECT IDENTIFIER ::= { nbroTrIsdn 23 } -- nbroTrIsdn w/Ab Sw
nbro523 OBJECT IDENTIFIER ::= { nbroTrIsdn 24 } -- nbroTrIsdn w/Bf Sw

--
-- the following identifiers are assigned under a3Com.products.brouter.nbroTrHuge
--

nbroTrhBp  OBJECT IDENTIFIER ::= { nbroTrHuge 1 } --nbroTrHuge w/BP SW
nbroTrhCp  OBJECT IDENTIFIER ::= { nbroTrHuge 2 } --nbroTrHuge w/CP SW
nbroTrhXw  OBJECT IDENTIFIER ::= { nbroTrHuge 3 } -- nbroTrHuge w/Ext WAN SW
nbroTrhCx OBJECT IDENTIFIER ::= { nbroTrHuge 4 } -- nbroTrHuge w/CX SW
nbroTrhBa OBJECT IDENTIFIER ::= { nbroTrHuge 5 } --nbroTrHuge w/Bndry Rtg. SW
nbroTrh322  OBJECT IDENTIFIER ::= { nbroTrHuge 6 } --nbroTrHuge w/AR SW
nbroTrhSn  OBJECT IDENTIFIER ::= { nbroTrHuge 7 } --nbroTrHuge w/SNA
nbroTrhRb OBJECT IDENTIFIER ::= { nbroTrHuge 8 } --nbroTrHuge w/RB SW
nbroTrhFf  OBJECT IDENTIFIER ::= { nbroTrHuge 9 } -- nbroTrHuge w/FF SW
nbroTrh327  OBJECT IDENTIFIER ::= { nbroTrHuge 10 }--nbroTrHuge w/CF SW
nbroTrh321     OBJECT IDENTIFIER ::= { nbroTrHuge 11 }--nbroTrHuge w/BX SW
nbroTrhAppn OBJECT IDENTIFIER ::= { nbroTrHuge 12 } -- nbroTrHuge w/Appn SW
nbroTrhLm OBJECT IDENTIFIER ::= { nbroTrHuge 13 } -- nbroTrHuge w/Lm Sw
nbroTrhLt OBJECT IDENTIFIER ::= { nbroTrHuge 14 } -- nbroTrHuge w/Lt Sw
nbroTrhWm OBJECT IDENTIFIER ::= { nbroTrHuge 15 } -- nbroTrHuge w/Wm Sw
nbroTrhWt OBJECT IDENTIFIER ::= { nbroTrHuge 16 } -- nbroTrHuge w/Wt Sw
nbroTrhAe OBJECT IDENTIFIER ::= { nbroTrHuge 17 } -- nbroTrHuge w/Ae Sw
nbroTrhAp OBJECT IDENTIFIER ::= { nbroTrHuge 18 } -- nbroTrHuge w/Ap Sw
nbroTrhAn OBJECT IDENTIFIER ::= { nbroTrHuge 19 } -- nbroTrHuge w/An Sw
nbroTrhLa OBJECT IDENTIFIER ::= { nbroTrHuge 20 } -- nbroTrHuge w/La Sw
nbroTrhWa OBJECT IDENTIFIER ::= { nbroTrHuge 21 } -- nbroTrHuge w/Wa Sw
nbroTrhAa OBJECT IDENTIFIER ::= { nbroTrHuge 22 } -- nbroTrHuge w/Aa Sw
nbroTrhAb OBJECT IDENTIFIER ::= { nbroTrHuge 23 } -- nbroTrHuge w/Ab Sw
nbroTrh323 OBJECT IDENTIFIER ::= { nbroTrHuge 24 } -- nbroTrHuge w/Bf Sw


--
-- the following identifiers are assigned under a3Com.products.brouter.officeConnRtr
--

ocRtrBp  OBJECT IDENTIFIER ::= { officeConnRtr 1 } --officeConnRtr w/BP SW
ocRtrCp  OBJECT IDENTIFIER ::= { officeConnRtr 2 } --officeConnRtr w/CP SW
ocRtrXw  OBJECT IDENTIFIER ::= { officeConnRtr 3 } -- officeConnRtr w/Ext WAN SW
ocRtrCx OBJECT IDENTIFIER ::= { officeConnRtr 4 } -- officeConnRtr w/CX SW
ocRtrBa OBJECT IDENTIFIER ::= { officeConnRtr 5 } --officeConnRtr w/Bndry Rtg. SW
ocRtrAr  OBJECT IDENTIFIER ::= { officeConnRtr 6 } --officeConnRtr w/AR SW
ocRtrSn  OBJECT IDENTIFIER ::= { officeConnRtr 7 } --officeConnRtr w/SNA
ocRtrRb OBJECT IDENTIFIER ::= { officeConnRtr 8 } --officeConnRtr w/RB SW
ocRtrFf  OBJECT IDENTIFIER ::= { officeConnRtr 9 } -- officeConnRtr w/FF SW
ocRtrCf  OBJECT IDENTIFIER ::= { officeConnRtr 10 }--officeConnRtr w/CF SW
ocRtrBx     OBJECT IDENTIFIER ::= { officeConnRtr 11 }--officeConnRtr w/BX SW
ocRtrAppn OBJECT IDENTIFIER ::= { officeConnRtr 12 } -- officeConnRtr w/Appn SW
ocRtrLm OBJECT IDENTIFIER ::= { officeConnRtr 13 } -- officeConnRtr w/Lm Sw
ocRtrLt OBJECT IDENTIFIER ::= { officeConnRtr 14 } -- officeConnRtr w/Lt Sw
ocRtrWm OBJECT IDENTIFIER ::= { officeConnRtr 15 } -- officeConnRtr w/Wm Sw
ocRtrWt OBJECT IDENTIFIER ::= { officeConnRtr 16 } -- officeConnRtr w/Wt Sw
ocRtrAe OBJECT IDENTIFIER ::= { officeConnRtr 17 } -- officeConnRtr w/Ae Sw
ocRtrAp OBJECT IDENTIFIER ::= { officeConnRtr 18 } -- officeConnRtr w/Ap Sw
ocRtrAn OBJECT IDENTIFIER ::= { officeConnRtr 19 } -- officeConnRtr w/An Sw
ocRtrLa OBJECT IDENTIFIER ::= { officeConnRtr 20 } -- officeConnRtr w/La Sw
ocRtrWa OBJECT IDENTIFIER ::= { officeConnRtr 21 } -- officeConnRtr w/Wa Sw
ocRtrAa OBJECT IDENTIFIER ::= { officeConnRtr 22 } -- officeConnRtr w/Aa Sw
ocRtrAb OBJECT IDENTIFIER ::= { officeConnRtr 23 } -- officeConnRtr w/Ab Sw
ocRtrBf OBJECT IDENTIFIER ::= { officeConnRtr 24 } -- officeConnRtr w/Bf Sw

--
-- the following identifiers are assigned to brouterBoards
--

ethernet      OBJECT IDENTIFIER ::= { brouterBoards 1 }
fddiPhy       OBJECT IDENTIFIER ::= { brouterBoards 2 }
fddiMac       OBJECT IDENTIFIER ::= { brouterBoards 3 }
hss           OBJECT IDENTIFIER ::= { brouterBoards 4 }
tokenRingBrd  OBJECT IDENTIFIER ::= { brouterBoards 5 }
hssG703       OBJECT IDENTIFIER ::= { brouterBoards 6 }
hssRS449      OBJECT IDENTIFIER ::= { brouterBoards 7 }
t3HSSI        OBJECT IDENTIFIER ::= { brouterBoards 8 } 
dualEth       OBJECT IDENTIFIER ::= { brouterBoards 9 }
cec           OBJECT IDENTIFIER ::= { brouterBoards 10 }
fddiPhySm     OBJECT IDENTIFIER ::= { brouterBoards 11 }
fddiPhyMmSm   OBJECT IDENTIFIER ::= { brouterBoards 12 }
fddiPhySmMm   OBJECT IDENTIFIER ::= { brouterBoards 13 } 
hdwan         OBJECT IDENTIFIER ::= { brouterBoards 14 } 
hdwan449      OBJECT IDENTIFIER ::= { brouterBoards 15 } 
hdwan232      OBJECT IDENTIFIER ::= { brouterBoards 16 }
mp6Eth        OBJECT IDENTIFIER ::= { brouterBoards 17 }
trPlus        OBJECT IDENTIFIER ::= { brouterBoards 18 }
macPlus       OBJECT IDENTIFIER ::= { brouterBoards 19 }
cecStar       OBJECT IDENTIFIER ::= { brouterBoards 20 }
isdnBri       OBJECT IDENTIFIER ::= { brouterBoards 21 }
isdnPri       OBJECT IDENTIFIER ::= { brouterBoards 22 }
mpAtm         OBJECT IDENTIFIER ::= { brouterBoards 23 }
hssI431       OBJECT IDENTIFIER ::= { brouterBoards 24 }
mpFddi        OBJECT IDENTIFIER ::= { brouterBoards 25 }
mp6EthFl      OBJECT IDENTIFIER ::= { brouterBoards 26 }
ethV3         OBJECT IDENTIFIER ::= { brouterBoards 27 }
ethV3Fl       OBJECT IDENTIFIER ::= { brouterBoards 28 }
nbroBrd       OBJECT IDENTIFIER ::= { brouterBoards 29 }
mpAtmFiber    OBJECT IDENTIFIER ::= { brouterBoards 30 }
cec2          OBJECT IDENTIFIER ::= { brouterBoards 31 }
flatFddiMm    OBJECT IDENTIFIER ::= { brouterBoards 32 }
flatFddiSs    OBJECT IDENTIFIER ::= { brouterBoards 33 }
flatFddiSm    OBJECT IDENTIFIER ::= { brouterBoards 34 }
flatFddiMs    OBJECT IDENTIFIER ::= { brouterBoards 35 }


--
-- the following identifiers are assigned to brouterBrdFwVers
--

noFw          OBJECT IDENTIFIER ::= { brouterBrdFwVers 1 }
cecFw         OBJECT IDENTIFIER ::= { brouterBrdFwVers 2 }
hdwanFw       OBJECT IDENTIFIER ::= { brouterBrdFwVers 3 }
hdwan232Fw    OBJECT IDENTIFIER ::= { brouterBrdFwVers 4 }
hdwan449Fw    OBJECT IDENTIFIER ::= { brouterBrdFwVers 5 }
mp6ethFw      OBJECT IDENTIFIER ::= { brouterBrdFwVers 6 }
cecStarFw     OBJECT IDENTIFIER ::= { brouterBrdFwVers 7 }
mpAtmFw       OBJECT IDENTIFIER ::= { brouterBrdFwVers 8 }
mpFddiFw      OBJECT IDENTIFIER ::= { brouterBrdFwVers 9 }
mp6EthFlFw    OBJECT IDENTIFIER ::= { brouterBrdFwVers 10 }
nbroFw        OBJECT IDENTIFIER ::= { brouterBrdFwVers 11 }


--
-- the following identifiers are assigned to brouterBrdSwVers
--

noSw          OBJECT IDENTIFIER ::= { brouterBrdSwVers 1 }
mp6eth        OBJECT IDENTIFIER ::= { brouterBrdSwVers 2 }

--
-- the following identifiers are assigned under a3Com.products.genericMSWorkstation
--

deskManProduct OBJECT IDENTIFIER ::= { genericMSWorkstation 1 }

--
-- the following identifiers are assigned under a3Com.products.genericMSWorkstation.deskManProduct
--

ethernetSoftHub  OBJECT IDENTIFIER ::= { deskManProduct 1 }
ethernetDTAnode  OBJECT IDENTIFIER ::= { deskManProduct 2 }
tokenRingSoftHub OBJECT IDENTIFIER ::= { deskManProduct 3 }
tokenRingDTAnode OBJECT IDENTIFIER ::= { deskManProduct 4 }

--
-- the following identifiers are assigned to 3com hubs
--

linkBuilder3GH              OBJECT IDENTIFIER ::= { hub 1 }
linkBuilder10BTi            OBJECT IDENTIFIER ::= { hub 2 }
linkBuilderECS              OBJECT IDENTIFIER ::= { hub 3 }
linkBuilderMSH              OBJECT IDENTIFIER ::= { hub 4 }
linkBuilderFMS              OBJECT IDENTIFIER ::= { hub 5 }
linkBuilderFddiWorkGroupHub OBJECT IDENTIFIER ::= { hub 6 }
linkBuilderFMSII            OBJECT IDENTIFIER ::= { hub 7 }
linkSwitchFMS               OBJECT IDENTIFIER ::= { hub 8 }
linkSwitchMSH               OBJECT IDENTIFIER ::= { hub 9 }
linkBuilderFMSLBridge       OBJECT IDENTIFIER ::= { hub 10 }
linkBuilderTP8i             OBJECT IDENTIFIER ::= { hub 11 }
linkBuilderMSHFddi          OBJECT IDENTIFIER ::= { hub 12 }
linkSwitch1000              OBJECT IDENTIFIER ::= { hub 13 }
linkSwitch500               OBJECT IDENTIFIER ::= { hub 14 }
linkSwitch2700AU            OBJECT IDENTIFIER ::= { hub 15 }
linkSwitch2700Bridge        OBJECT IDENTIFIER ::= { hub 16 }
linkBuilderFMS100LBridge    OBJECT IDENTIFIER ::= { hub 17 }
linkSwitch2700TliAU         OBJECT IDENTIFIER ::= { hub 18 }
linkSwitch2700TliBridge     OBJECT IDENTIFIER ::= { hub 19 }
linkBuilderFMS100           OBJECT IDENTIFIER ::= { hub 20 }
officeConnect-Hub8M         OBJECT IDENTIFIER ::= { hub 21 }
linkSwitch3000              OBJECT IDENTIFIER ::= { hub 22 }
mshSwitch                   OBJECT IDENTIFIER ::= { hub 23 }
linkSwitch2000TR            OBJECT IDENTIFIER ::= { hub 24 }
oncoreFastModuleFPA100    OBJECT IDENTIFIER ::= { hub 25}
oncoreFastModuleFPA10      OBJECT IDENTIFIER ::= { hub 26}
oncoreFastModuleFPA10FX OBJECT IDENTIFIER ::= { hub 27} 
oncoreFastModuleBPA           OBJECT IDENTIFIER ::= { hub 28}              
superStackDesktopSwitch   OBJECT IDENTIFIER ::= { hub 29 }

--
-- the following identifiers are assigned to 3com atm switching products
--

cELLplex7000             OBJECT IDENTIFIER ::= { atm 1 }
cELLplex7000-cards       OBJECT IDENTIFIER ::= { atm 2 }

--
-- the following identifiers are assigned to 3com cELLplex7000 interface cards
--

cELLplex-7x00cardBridge       OBJECT IDENTIFIER ::= { cELLplex7000-cards 1 }
cELLplex-7200card             OBJECT IDENTIFIER ::= { cELLplex7000-cards 2 }
cELLplex-7200Fcard            OBJECT IDENTIFIER ::= { cELLplex7000-cards 3 }
cELLplex-7400card             OBJECT IDENTIFIER ::= { cELLplex7000-cards 4 }
cELLplex-7600card             OBJECT IDENTIFIER ::= { cELLplex7000-cards 5 }

--
-- the following identifiers are assigned to 3com modules and cards
--

linkBuilder3GH-cards              OBJECT IDENTIFIER ::= { cards 1 }
linkBuilder10BTi-cards            OBJECT IDENTIFIER ::= { cards 2 }
linkBuilderECS-cards              OBJECT IDENTIFIER ::= { cards 3 }
linkBuilderMSH-cards              OBJECT IDENTIFIER ::= { cards 4 }
linkBuilderFMS-cards              OBJECT IDENTIFIER ::= { cards 5 }
linkBuilderFMSII-cards            OBJECT IDENTIFIER ::= { cards 6 } 
a3C512                            OBJECT IDENTIFIER ::= { cards 7 }
linkBuilderTP8i-cards             OBJECT IDENTIFIER ::= { cards 8 }
linkSwitch1000-cards              OBJECT IDENTIFIER ::= { cards 9 }
linkBuilderFMS100-cards           OBJECT IDENTIFIER ::= { cards 10 } 
officeConnect-Hub8M-cards         OBJECT IDENTIFIER ::= { cards 11 } 
linkSwitch2000TR-cards            OBJECT IDENTIFIER ::= { cards 12 }

linkBuilder10BTi-cards-utp        OBJECT IDENTIFIER ::= { linkBuilder10BTi-cards 1 }
linkBuilder10BT-cards-utp         OBJECT IDENTIFIER ::= { linkBuilder10BTi-cards 2 }

linkBuilderFMS-cards-utp          OBJECT IDENTIFIER ::= { linkBuilderFMS-cards 1 }
linkBuilderFMS-cards-coax         OBJECT IDENTIFIER ::= { linkBuilderFMS-cards 2 }
linkBuilderFMS-cards-fiber        OBJECT IDENTIFIER ::= { linkBuilderFMS-cards 3 }
linkBuilderFMS-cards-12fiber      OBJECT IDENTIFIER ::= { linkBuilderFMS-cards 4 }
linkBuilderFMS-cards-24utp        OBJECT IDENTIFIER ::= { linkBuilderFMS-cards 5 }

linkBuilderFMSII-cards-12tp-rj45  OBJECT IDENTIFIER ::= { linkBuilderFMSII-cards 1 }
linkBuilderFMSII-cards-10coax-bnc OBJECT IDENTIFIER ::= { linkBuilderFMSII-cards 2 }
linkBuilderFMSII-cards-6fiber-st  OBJECT IDENTIFIER ::= { linkBuilderFMSII-cards 3 }
linkBuilderFMSII-cards-12fiber-st OBJECT IDENTIFIER ::= { linkBuilderFMSII-cards 4 } 
linkBuilderFMSII-cards-24tp-rj45  OBJECT IDENTIFIER ::= { linkBuilderFMSII-cards 5 } 
linkBuilderFMSII-cards-24tp-telco OBJECT IDENTIFIER ::= { linkBuilderFMSII-cards 6 }
superStackHub10-cards-12tp-rj45   OBJECT IDENTIFIER ::= { linkBuilderFMSII-cards 7 }
superStackHub10-cards-24tp-rj45   OBJECT IDENTIFIER ::= { linkBuilderFMSII-cards 8 } 
superStackHub10-cards-6fiber-st   OBJECT IDENTIFIER ::= { linkBuilderFMSII-cards 9 }
superStackHub10-cards-24tp-telco  OBJECT IDENTIFIER ::= { linkBuilderFMSII-cards 10 }

a3C512-withBNC-expn-card          OBJECT IDENTIFIER ::= { a3C512 1 }
a3C512-withAUI-expn-card          OBJECT IDENTIFIER ::= { a3C512 2 }
a3C512-withFOIRL-expn-card        OBJECT IDENTIFIER ::= { a3C512 3 }

linkBuilderTP8i-cards-8tp-rj45    OBJECT IDENTIFIER ::= { linkBuilderTP8i-cards 1 }

linkSwitch1000-cards-24tp-rj45    OBJECT IDENTIFIER ::= { linkSwitch1000-cards 1 }
linkSwitch1000-cards-12tp-rj45    OBJECT IDENTIFIER ::= { linkSwitch1000-cards 2 }
linkSwitch3000-cards-5fiber-sc    OBJECT IDENTIFIER ::= { linkSwitch1000-cards 3 }
linkSwitch3000-cards-8tp-rj45     OBJECT IDENTIFIER ::= { linkSwitch1000-cards 4 }

superStackSwitch1000-cards-24tp-rj45    OBJECT IDENTIFIER ::= { linkSwitch1000-cards 5 }
superStackSwitch1000-cards-12tp-rj45    OBJECT IDENTIFIER ::= { linkSwitch1000-cards 6 }
superStackSwitch3000-cards-5fiber-sc    OBJECT IDENTIFIER ::= { linkSwitch1000-cards 7 }
superStackSwitch3000-cards-8tp-rj45     OBJECT IDENTIFIER ::= { linkSwitch1000-cards 8 }

oncore-cards-5fiber-sc-2tp-rj45-blk       OBJECT IDENTIFIER ::= { linkSwitch1000-cards 9}   
oncore-cards-24tp-telco-blk                    OBJECT IDENTIFIER ::= { linkSwitch1000-cards 10 }   
oncore-cards-24tp-telco-1fiber-sc-blk  OBJECT IDENTIFIER ::= { linkSwitch1000-cards 11}    
oncore-cards-1fiber-sc-7blk                    OBJECT IDENTIFIER ::= { linkSwitch1000-cards 12}   

superStackSwitch1000-3000-cards-atm  OBJECT IDENTIFIER ::= { linkSwitch1000-cards 13 }

oncore-cards-2fiber-sc-7blk               OBJECT IDENTIFIER ::= { linkSwitch1000-cards 14}  
oncore-cards-1fiber-sc-tp-rj45-7blk OBJECT IDENTIFIER ::= { linkSwitch1000-cards 15}  
oncore-cards-1fiber-sc-atm-7blk     OBJECT IDENTIFIER ::= { linkSwitch1000-cards 16}
superStackDesktopSwitch-24tp-rj45  OBJECT IDENTIFIER  ::= { linkSwitch1000-cards 17}

linkBuilderFMS100-cards-12utp     OBJECT IDENTIFIER ::= { linkBuilderFMS100-cards 1 }  -- this is Ethernet 100BaseTX repeater card
linkBuilderFMS100-cards-12T4      OBJECT IDENTIFIER ::= { linkBuilderFMS100-cards 2 }  -- this is Ethernet 100BaseT4 repeater card

officeConnect-Hub8M-cards-8tp-rj45  OBJECT IDENTIFIER ::= { officeConnect-Hub8M-cards 1 }

linkSwitch2000TR-cards-12tp-rj45    OBJECT IDENTIFIER ::= { linkSwitch2000TR-cards 1 }

--
-- the following identifiers are assigned to 3com chip sets
--

valcan         OBJECT IDENTIFIER ::= { chipSets 1 }

--
-- the following identifiers are assigned to 3com oem products
--

linkConv250   OBJECT IDENTIFIER ::= { oem 1 }
linkConv251   OBJECT IDENTIFIER ::= { oem 2 }
linkConv350   OBJECT IDENTIFIER ::= { oem 3 }
linkConv351   OBJECT IDENTIFIER ::= { oem 4 }

--
-- the following identifiers are assigned to Synernetics products
--     (SysOID 1.3.6.1.4.1.114)  
--

synernetics             OBJECT IDENTIFIER ::= { enterprises 114 }
lanplex                 OBJECT IDENTIFIER ::= { synernetics 1 }

lANplex-12-slot-support OBJECT IDENTIFIER ::= { lanplex 1 }
lANplex-4-slot-support  OBJECT IDENTIFIER ::= { lanplex 2 }

lpsProducts             OBJECT IDENTIFIER ::= { lanplex 3 }

--
-- the following identifiers are assigned to the LANplex product line
--

lps6000                 OBJECT IDENTIFIER ::= { lpsProducts 2 }
lps2000                 OBJECT IDENTIFIER ::= { lpsProducts 3 }

-- 
-- the following identifiers are assigned to the LANplex product types
--

lps6012                 OBJECT IDENTIFIER ::= { lps6000 1 }
lps6004                 OBJECT IDENTIFIER ::= { lps6000 2 }

lps2500                 OBJECT IDENTIFIER ::= { lps2000 1 }
lss2200                 OBJECT IDENTIFIER ::= { lps2000 2 }
lps2016                 OBJECT IDENTIFIER ::= { lps2000 3 }
lss2200SS2        OBJECT IDENTIFIER ::= { lps2000 4 }

--
-- the following identifiers are assigned to the LANplex 6000 devices
--

lps6012System           OBJECT IDENTIFIER ::= { lps6012 1 }
lps6012Chassis          OBJECT IDENTIFIER ::= { lps6012 2 }
lps6012ESM              OBJECT IDENTIFIER ::= { lps6012 3 }
lps6012EFSM             OBJECT IDENTIFIER ::= { lps6012 4 }
lps6012TRSM  OBJECT IDENTIFIER ::= { lps6012 5 }
lps6012TMM  OBJECT IDENTIFIER ::= { lps6012 6 }
lps6012FSM  OBJECT IDENTIFIER ::= { lps6012 7 } 

lps6004System           OBJECT IDENTIFIER ::= { lps6004 1 }
lps6004Chassis          OBJECT IDENTIFIER ::= { lps6004 2 }
lps6004ESM              OBJECT IDENTIFIER ::= { lps6004 3 }
lps6004EFSM             OBJECT IDENTIFIER ::= { lps6004 4 }
lps6004TRSM  OBJECT IDENTIFIER ::= { lps6004 5 }
lps6004TMM  OBJECT IDENTIFIER ::= { lps6004 6 }
lps6004FSM  OBJECT IDENTIFIER ::= { lps6004 7 } 

--
-- the following identifiers are assigned to the LANplex agent versions
--

lanplex-2500-2          OBJECT IDENTIFIER ::= { lps2500 2 }
lanplex-2500-3          OBJECT IDENTIFIER ::= { lps2500 3 }
lanplex-2500-4          OBJECT IDENTIFIER ::= { lps2500 4 }
lanplex-2500-5          OBJECT IDENTIFIER ::= { lps2500 5 }
lanplex-2500-6          OBJECT IDENTIFIER ::= { lps2500 6 }

linkSwitch-2200-2       OBJECT IDENTIFIER ::= { lss2200 2 }
linkSwitch-2200-3       OBJECT IDENTIFIER ::= { lss2200 3 }
linkSwitch-2200-4       OBJECT IDENTIFIER ::= { lss2200 4 }
linkSwitch-2200-5       OBJECT IDENTIFIER ::= { lss2200 5 }
linkSwitch-2200-6       OBJECT IDENTIFIER ::= { lss2200 6 }

lanplex-2016-2          OBJECT IDENTIFIER ::= { lps2016 2 }
lanplex-2016-3          OBJECT IDENTIFIER ::= { lps2016 3 }
lanplex-2016-4          OBJECT IDENTIFIER ::= { lps2016 4 }
lanplex-2016-5          OBJECT IDENTIFIER ::= { lps2016 5 }
lanplex-2016-6          OBJECT IDENTIFIER ::= { lps2016 6 }

linkSwitch-2200-SS2-7       OBJECT IDENTIFIER ::= { lss2200SS2 7 }

lanplex-6012-System-2   OBJECT IDENTIFIER ::= { lps6012System 2 }
lanplex-6012-System-3   OBJECT IDENTIFIER ::= { lps6012System 3 }
lanplex-6012-System-4   OBJECT IDENTIFIER ::= { lps6012System 4 }
lanplex-6012-System-5   OBJECT IDENTIFIER ::= { lps6012System 5 }
lanplex-6012-System-6   OBJECT IDENTIFIER ::= { lps6012System 6 }

lanplex-6012-Chassis-2  OBJECT IDENTIFIER ::= { lps6012Chassis 2 }
lanplex-6012-Chassis-3  OBJECT IDENTIFIER ::= { lps6012Chassis 3 }
lanplex-6012-Chassis-4  OBJECT IDENTIFIER ::= { lps6012Chassis 4 }
lanplex-6012-Chassis-5  OBJECT IDENTIFIER ::= { lps6012Chassis 5 }
lanplex-6012-Chassis-6  OBJECT IDENTIFIER ::= { lps6012Chassis 6 }

lanplex-6012-ESM-2      OBJECT IDENTIFIER ::= { lps6012ESM 2 }
lanplex-6012-ESM-3      OBJECT IDENTIFIER ::= { lps6012ESM 3 }
lanplex-6012-ESM-4      OBJECT IDENTIFIER ::= { lps6012ESM 4 }
lanplex-6012-ESM-5      OBJECT IDENTIFIER ::= { lps6012ESM 5 }
lanplex-6012-ESM-6      OBJECT IDENTIFIER ::= { lps6012ESM 6 }

lanplex-6012-EFSM-2     OBJECT IDENTIFIER ::= { lps6012EFSM 2 }
lanplex-6012-EFSM-3     OBJECT IDENTIFIER ::= { lps6012EFSM 3 }
lanplex-6012-EFSM-4     OBJECT IDENTIFIER ::= { lps6012EFSM 4 }
lanplex-6012-EFSM-5     OBJECT IDENTIFIER ::= { lps6012EFSM 5 }
lanplex-6012-EFSM-6     OBJECT IDENTIFIER ::= { lps6012EFSM 6 }

lanplex-6012-TRSM-5     OBJECT IDENTIFIER ::= { lps6012TRSM 5 }
lanplex-6012-TRSM-6     OBJECT IDENTIFIER ::= { lps6012TRSM 6 }

lanplex-6012-TMM-6     OBJECT IDENTIFIER ::= { lps6012TMM 6 }

lanplex-6012-FSM-7     OBJECT IDENTIFIER ::= { lps6012FSM 7 }

lanplex-6004-System-2   OBJECT IDENTIFIER ::= { lps6004System 2 }
lanplex-6004-System-3   OBJECT IDENTIFIER ::= { lps6004System 3 }
lanplex-6004-System-4   OBJECT IDENTIFIER ::= { lps6004System 4 }
lanplex-6004-System-5   OBJECT IDENTIFIER ::= { lps6004System 5 }
lanplex-6004-System-6   OBJECT IDENTIFIER ::= { lps6004System 6 }

lanplex-6004-Chassis-2  OBJECT IDENTIFIER ::= { lps6004Chassis 2 }
lanplex-6004-Chassis-3  OBJECT IDENTIFIER ::= { lps6004Chassis 3 }
lanplex-6004-Chassis-4  OBJECT IDENTIFIER ::= { lps6004Chassis 4 }
lanplex-6004-Chassis-5  OBJECT IDENTIFIER ::= { lps6004Chassis 5 }
lanplex-6004-Chassis-6  OBJECT IDENTIFIER ::= { lps6004Chassis 6 }

lanplex-6004-ESM-2      OBJECT IDENTIFIER ::= { lps6004ESM 2 }
lanplex-6004-ESM-3      OBJECT IDENTIFIER ::= { lps6004ESM 3 }
lanplex-6004-ESM-4      OBJECT IDENTIFIER ::= { lps6004ESM 4 }
lanplex-6004-ESM-5      OBJECT IDENTIFIER ::= { lps6004ESM 5 }
lanplex-6004-ESM-6      OBJECT IDENTIFIER ::= { lps6004ESM 6 }

lanplex-6004-EFSM-2     OBJECT IDENTIFIER ::= { lps6004EFSM 2 }
lanplex-6004-EFSM-3     OBJECT IDENTIFIER ::= { lps6004EFSM 3 }
lanplex-6004-EFSM-4     OBJECT IDENTIFIER ::= { lps6004EFSM 4 }
lanplex-6004-EFSM-5     OBJECT IDENTIFIER ::= { lps6004EFSM 5 }
lanplex-6004-EFSM-6     OBJECT IDENTIFIER ::= { lps6004EFSM 6 }

lanplex-6004-TRSM-5     OBJECT IDENTIFIER ::= { lps6004TRSM 5 }
lanplex-6004-TRSM-6     OBJECT IDENTIFIER ::= { lps6004TRSM 6 }

lanplex-6004-TMM-6     OBJECT IDENTIFIER ::= { lps6004TMM 6 }

lanplex-6004-FSM-7     OBJECT IDENTIFIER ::= { lps6004FSM 7 }

--
-- the following identifier are assigned to the LANplex MIB modules
--

lanplexSystemsMib       OBJECT IDENTIFIER ::= { lanplex 4 }
lanplexOptFddi          OBJECT IDENTIFIER ::= { lanplex 10 }

--
-- the following identifiers are assigned to Centrum products
--     (SysOID 1.3.6.1.4.1.327)  
--

centrum        OBJECT IDENTIFIER ::= { enterprises 327 }
mibDoc         OBJECT IDENTIFIER ::= { centrum 1 }
centrumRemote  OBJECT IDENTIFIER ::= { mibDoc 1 }

--
-- for the older ISOLAN equipment
--

bicc            OBJECT IDENTIFIER ::= { enterprises 170 }
bdn             OBJECT IDENTIFIER ::= { bicc 1 }
bdnDevices      OBJECT IDENTIFIER ::= { bdn 1 }

END
